module openconfig-network-instance-ext {

  yang-version "1";

  // namespace
  namespace "http://openconfig.net/yang/network-instance/extension";

  prefix "oc-netinst-ext";
  
  import ietf-yang-types { prefix ietf; }
  import sonic-codegen { prefix sonic-codegen; }
  // import some basic types
  import openconfig-network-instance { prefix "oc-netinst"; }
  import openconfig-extensions { prefix oc-ext; }
  import openconfig-interfaces { prefix "oc-if"; }

  organization
      "SONiC";

  contact
      "SONiC";

  description
        "This module describes a YANG model for network instance
        configuration extensions.";

  oc-ext:openconfig-version "0.1.0";

  revision "2020-10-05" {
    description
      "Deviating range and default value for mac-aging-time.";
    reference "0.1.0";
  }

  grouping network-instance-ext-global-sag-config {

    description
      "Global static anycast gateway config";

	  leaf anycast-mac {
		  type ietf:mac-address;

		  description
			  "static anycast gateway MAC addresses";

	  }

    leaf ipv4-enable {
      type boolean;
		  default true;

      description
        "static anycast gateway IPv4 enable";
    }

    leaf ipv6-enable {
      type boolean;
		  default true;

      description
        "static anycast gateway IPv6 enable";
    }
  }

  grouping network-instance-ext-global-sag-top {
    description
      "Global static anycast gateway";
	  container global-sag {
		  container config {
			  uses network-instance-ext-global-sag-config;

        description
          "Global static anycast gateway config";
		  }
		  container state {
			  config false;
			  uses network-instance-ext-global-sag-config;

        description
          "Global static anycast gateway state";
		  }

      description
        "Static anycast gateway";
	  }
  }

  augment "/oc-netinst:network-instances/oc-netinst:network-instance" {
      description
          "Global Anycast Gateway";
      uses network-instance-ext-global-sag-top;
  }

  deviation /oc-netinst:network-instances/oc-netinst:network-instance/oc-netinst:fdb/oc-netinst:config/oc-netinst:mac-aging-time {
      sonic-codegen:lint-ignore "Deviated to be aligned with other vendors.";
      deviate replace {
          type uint32 {
              range 0..1000000{
                  error-message "Invalid MAC-aging value 0-1000000";
              }
          }
      }
      deviate add {
          default 600;
      }
  }
}
