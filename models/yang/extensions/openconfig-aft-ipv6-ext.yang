module openconfig-aft-ipv6-ext {

  yang-version "1";

  // namespace
  namespace "http://openconfig.net/yang/aft-ipv6/extension";

  prefix "oc-aft-ipv6-ext";

  // import some basic types
  import openconfig-network-instance { prefix oc-netinst; }
  import openconfig-aft { prefix oc-aft; }
  import openconfig-aft-ext { prefix oc-aft-ext; }
  import openconfig-extensions { prefix oc-ext; }

  organization
      "SONiC";

  contact
      "SONiC";

  description
    "This module describes a deviation for network instance afts-ipv6
     extensions.";

  oc-ext:openconfig-version "0.1.0";

  revision "2019-11-13" {
    description
      "Network instance aft-ipv6 extensions.";

    reference "0.1.0";
  }

  augment /oc-netinst:network-instances/oc-netinst:network-instance/oc-netinst:afts/oc-netinst:ipv6-unicast/oc-netinst:ipv6-entry {
      description "AFT extensions for IPv6 forwarding entry";
      uses oc-aft:aft-nhop-structural;
  }

  augment /oc-netinst:network-instances/oc-netinst:network-instance/oc-netinst:afts/oc-netinst:ipv6-unicast/oc-netinst:ipv6-entry/oc-netinst:state {
      description "AFT extensions for IPv6 forwarding entry state";
      uses oc-aft-ext:aft-ext-common-ip-state;
  }
  augment /oc-netinst:network-instances/oc-netinst:network-instance/oc-netinst:afts/oc-netinst:ipv6-unicast/oc-netinst:ipv6-entry/next-hops/next-hop/state {
      description "AFT nexthop state extensions for IPv6 forwarding entry";
      uses oc-aft-ext:aft-ext-common-entry-nexthop-state;
  }
}
