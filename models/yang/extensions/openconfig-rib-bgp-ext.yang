module openconfig-rib-bgp-ext {

  yang-version "1";

  // namespace
  namespace "http://openconfig.net/yang/rib-bgp/extension";

  prefix "oc-bgprib-ext";

  import openconfig-extensions { prefix oc-ext; }
  import openconfig-rib-bgp-types { prefix oc-bgpribt; }
  import openconfig-network-instance { prefix oc-ni; }
  import openconfig-inet-types { prefix oc-inet; }
  import openconfig-rib-bgp { prefix oc-rib-bgp; }
  import openconfig-policy-types { prefix oc-pol-types; }
  import openconfig-bgp-ext { prefix oc-bgp-ext; }
  import openconfig-yang-types { prefix oc-yang; }
  import openconfig-bgp-evpn-ext { prefix oc-bgp-evpn-ext; }
  organization
      "SONiC";

  contact
      "SONiC";

  description
    "Defines additional data nodes for the OpenConfig BGP RIB model.
    These items reflect extensions that are desirable features but
    are not currently supported in a majority of BGP
    implementations.";

  oc-ext:openconfig-version "0.6.0";

  revision "2019-04-25" {
    description
      "Update last-modified timestamp to be expressed as nanoseconds
      since the Unix epoch.";
    reference "0.6.0";
  }

  revision "2019-04-16" {
    description
      "Rename the top-level BGP RIB container's name
      to RIB.";
    reference "0.5.0";
  }

  revision "2019-02-27" {
    description
      "Remove top-level BGP RIB container, and update list
      names to be compatible with path compression.";
    reference "0.4.0";
  }

  revision "2018-11-21" {
    description
      "Add OpenConfig module metadata extensions.";
    reference "0.3.1";
  }

  revision "2016-10-17" {
    description
      "OpenConfig BGP RIB refactor";
    reference "0.3.0";
  }

  revision "2016-04-11" {
    description
      "OpenConfig public release";
    reference "0.2.0";
  }

  // OpenConfig specific extensions for module metadata.
  oc-ext:regexp-posix;
  oc-ext:catalog-organization "openconfig";
  oc-ext:origin "openconfig";

  grouping rib-bgp-ext-route-annotations-state {
    description
      "Extended annotations for routes in the routing tables";

    leaf reject-reason {
      type union {
        type identityref {
          base oc-bgpribt:BGP_NOT_SELECTED_BESTPATH;
        }
        type identityref {
          base oc-bgpribt:BGP_NOT_SELECTED_POLICY;
        }
      }
      description
        "Indicates the reason the route is not used, either due to
        policy filtering or bestpath selection";
    }
  }

  grouping rib-bgp-ext-route-bestpath-annotations-state {
    leaf best-path {
       type boolean;
         description
           "Current path was selected as the best path.";
    }
    description
      "Current path was selected as the best path.";
  }

  augment "/oc-ni:network-instances/oc-ni:network-instance/" +
    "oc-ni:protocols/oc-ni:protocol/" +
    "oc-ni:bgp/oc-ni:rib/oc-ni:afi-safis/" +
    "oc-ni:afi-safi/oc-ni:ipv4-unicast/oc-ni:loc-rib/" +
    "oc-ni:routes/oc-ni:route/oc-ni:state" {
      description
        "Add extended annotations to the Loc-RIB for IPv4";

      uses rib-bgp-ext-route-annotations-state;
      uses rib-bgp-ext-route-bestpath-annotations-state;
  }

  augment "/oc-ni:network-instances/oc-ni:network-instance/" +
    "oc-ni:protocols/oc-ni:protocol" +
    "/oc-ni:bgp/oc-ni:rib/oc-ni:afi-safis/" +
    "oc-ni:afi-safi/oc-ni:ipv6-unicast/oc-ni:loc-rib/" +
    "oc-ni:routes/oc-ni:route/oc-ni:state" {
      description
        "Add extended annotations to the Loc-RIB for IPv6";

      uses rib-bgp-ext-route-annotations-state;
      uses rib-bgp-ext-route-bestpath-annotations-state;
  }

  augment "/oc-ni:network-instances/oc-ni:network-instance/" +
    "oc-ni:protocols/oc-ni:protocol" +
    "/oc-ni:bgp/oc-ni:rib/oc-ni:afi-safis/" +
    "oc-ni:afi-safi/oc-ni:ipv4-unicast/" +
    "oc-ni:neighbors/oc-ni:neighbor/" +
    "oc-ni:adj-rib-in-pre/oc-ni:routes/oc-ni:route" +
    "/oc-ni:state" {
      description
        "Add extended annotations to Adj-RIB for IPv4";

      uses rib-bgp-ext-route-annotations-state;
      uses rib-bgp-ext-route-bestpath-annotations-state;
  }

  augment
    "/oc-ni:network-instances/oc-ni:network-instance/" +
    "oc-ni:protocols/oc-ni:protocol" +
    "/oc-ni:bgp/oc-ni:rib/oc-ni:afi-safis/" +
    "oc-ni:afi-safi/oc-ni:ipv4-unicast/" +
    "oc-ni:neighbors/oc-ni:neighbor/" +
    "oc-ni:adj-rib-in-post/oc-ni:routes/oc-ni:route" +
    "/oc-ni:state"{
      description
        "Add extended annotations to Adj-RIB for IPv4";

      uses rib-bgp-ext-route-annotations-state;
  }

  augment "/oc-ni:network-instances/oc-ni:network-instance/" +
    "oc-ni:protocols/oc-ni:protocol" +
    "/oc-ni:bgp/oc-ni:rib/oc-ni:afi-safis/" +
    "oc-ni:afi-safi/oc-ni:ipv4-unicast/" +
    "oc-ni:neighbors/oc-ni:neighbor/" +
    "oc-ni:adj-rib-out-post/oc-ni:routes/oc-ni:route" +
    "/oc-ni:state"{
      description
        "Add extended annotations to Adj-RIB for IPv4";

      uses rib-bgp-ext-route-annotations-state;
      uses rib-bgp-ext-route-bestpath-annotations-state;
  }

  augment "/oc-ni:network-instances/oc-ni:network-instance/" +
    "oc-ni:protocols/oc-ni:protocol" +
    "/oc-ni:bgp/oc-ni:rib/oc-ni:afi-safis/" +
    "oc-ni:afi-safi/oc-ni:ipv6-unicast/" +
    "oc-ni:neighbors/oc-ni:neighbor/" +
    "oc-ni:adj-rib-in-pre/oc-ni:routes/oc-ni:route" +
    "/oc-ni:state"{
      description
        "Add extended annotations to Adj-RIB for IPv6";

      uses rib-bgp-ext-route-annotations-state;
      uses rib-bgp-ext-route-bestpath-annotations-state;
  }

  augment "/oc-ni:network-instances/oc-ni:network-instance/" +
    "oc-ni:protocols/oc-ni:protocol" +
    "/oc-ni:bgp/oc-ni:rib/oc-ni:afi-safis/" +
    "oc-ni:afi-safi/oc-ni:ipv6-unicast/" +
    "oc-ni:neighbors/oc-ni:neighbor/" +
    "oc-ni:adj-rib-in-post/oc-ni:routes/oc-ni:route" +
    "/oc-ni:state"{
      description
        "Add extended annotations to Adj-RIB for IPv6";

      uses rib-bgp-ext-route-annotations-state;
  }

  augment "/oc-ni:network-instances/oc-ni:network-instance/" +
    "oc-ni:protocols/oc-ni:protocol" +
    "/oc-ni:bgp/oc-ni:rib/oc-ni:afi-safis/" +
    "oc-ni:afi-safi/oc-ni:ipv6-unicast/" +
    "oc-ni:neighbors/oc-ni:neighbor/" +
    "oc-ni:adj-rib-out-post/oc-ni:routes/oc-ni:route" +
    "/oc-ni:state"{
      description
        "Add extended annotations to Adj-RIB for IPv6";

      uses rib-bgp-ext-route-annotations-state;
      uses rib-bgp-ext-route-bestpath-annotations-state;
  }

  grouping rib-bgp-ext-prefix-paths-top {
    description
      "Top-level grouping for IPv4 routing tables for prefix";

    container loc-rib-prefix-paths {
      config false;
      description
        "Container for the IPv4 BGP LOC-RIB data for prefix";

      container paths {
        description
          "Enclosing container for list of routes in the routing
          table.";

        list path {
          key "origin path-id";

          description
            "List of routes in the table, keyed by the route
            prefix, the route origin, and path-id.  The route
            origin can be either the neighbor address from which
            the route was learned, or the source protocol that
            injected the route.  The path-id distinguishes routes
            for the same prefix received from a neighbor (e.g.,
            if add-paths is eanbled).";

          leaf origin {
              type leafref {
                  path "../state/origin";
              }
              description
                  "Reference to the origin list key";
          }

          leaf path-id {
              type leafref {
                  path "../state/path-id";
              }
              description
                  "Reference to the path-id list key";
          }

          container state {
            description
              "Operational state data for route entries in the
              BGP LOC-RIB";

            leaf origin {
                type union {
                    type oc-inet:ip-address;
                    type identityref {
                        base oc-pol-types:INSTALL_PROTOCOL_TYPE;
                    }
                }
                description
                    "Indicates the origin of the route.  If the route is learned
                    from a neighbor, this value is the neighbor address.  If
                    the route was injected or redistributed from another
                    protocol, the origin indicates the source protocol for the
                    route.";
            }

            leaf path-id {
                type uint32;
                default 0;
                description
                    "If the route is learned from a neighbor, the path-id
                    corresponds to the path-id for the route in the
                    corresponding adj-rib-in-post table.  If the route is
                    injected from another protocol, or the neighbor does not
                    support BGP add-paths, the path-id should be set
                    to zero, also the default value.";
            }
            
            leaf remote-router-id {
                type oc-yang:dotted-quad;
                description
                    "A identifier for the remote network instance - typically
                    used within associated routing protocols or signalling
                    routing information in another network instance";
            }

            leaf best-path {
                type boolean;
                description
                    "Current path was selected as the best path.";
            }

            uses rib-bgp-ext-route-annotations-state;
            uses oc-rib-bgp:bgp-loc-rib-attr-state;
            uses oc-rib-bgp:bgp-common-route-annotations-state;
            uses oc-rib-bgp:bgp-loc-rib-route-annotations-state;
          }
          uses oc-rib-bgp:bgp-unknown-attr-top;
          uses oc-bgp-ext:bgp-ext-attr-sets-state;
        }
      }
    }
  }

  grouping rib-bgp-ext-ipv4-loc-rib-prefix-top {
    description
      "Top-level grouping for IPv4 routing tables for prefix";

    container loc-rib-prefix {
      config false;
      description
        "Container for the IPv4 BGP LOC-RIB data for prefix";

      uses oc-rib-bgp:bgp-common-table-attrs-top;

      container routes {
        description
          "Enclosing container for list of routes in the routing
          table.";

        list route {
          key "prefix";

          description
            "List of routes in the table, keyed by the route
            prefix, the route origin, and path-id.  The route
            origin can be either the neighbor address from which
            the route was learned, or the source protocol that
            injected the route.  The path-id distinguishes routes
            for the same prefix received from a neighbor (e.g.,
            if add-paths is eanbled).";

          leaf prefix {
              type leafref {
                  path "../state/prefix";
              }
              description
                  "Reference to the prefix list key";
          }

          container state {
            description
              "Operational state data for route entries in the
              BGP LOC-RIB";

            leaf prefix {
              type oc-inet:ipv4-prefix;
              description
                "The IPv4 prefix corresponding to the route";
            }
          }
          uses rib-bgp-ext-prefix-paths-top;
        }
      }
    }
  }

  grouping rib-bgp-ext-ipv6-loc-rib-prefix-top {
    description
      "Top-level grouping for IPv6 routing tables for prefix";

    container loc-rib-prefix {
      config false;
      description
        "Container for the IPv6 BGP LOC-RIB data for prefix";

      uses oc-rib-bgp:bgp-common-table-attrs-top;

      container routes {
        description
          "Enclosing container for list of routes in the routing
          table.";

        list route {
          key "prefix";

          description
            "List of routes in the table, keyed by the route
            prefix, the route origin, and path-id.  The route
            origin can be either the neighbor address from which
            the route was learned, or the source protocol that
            injected the route.  The path-id distinguishes routes
            for the same prefix received from a neighbor (e.g.,
            if add-paths is eanbled).";

          leaf prefix {
              type leafref {
                  path "../state/prefix";
              }
              description
                  "Reference to the prefix list key";
          }

          container state {
            description
              "Operational state data for route entries in the
              BGP LOC-RIB";

            leaf prefix {
              type oc-inet:ipv6-prefix;
              description
                "The IPv6 prefix corresponding to the route";
            }
          }
          uses rib-bgp-ext-prefix-paths-top;
        }
      }
    }
  }

  augment "/oc-ni:network-instances/oc-ni:network-instance/" +
    "oc-ni:protocols/oc-ni:protocol/" +
    "oc-ni:bgp/oc-ni:rib/oc-ni:afi-safis/" +
    "oc-ni:afi-safi/oc-ni:ipv4-unicast" {
      description
        "Add extended annotations for prefix based Loc-RIB for IPv4";

      uses rib-bgp-ext-ipv4-loc-rib-prefix-top;
  }

  augment "/oc-ni:network-instances/oc-ni:network-instance/" +
    "oc-ni:protocols/oc-ni:protocol/" +
    "oc-ni:bgp/oc-ni:rib/oc-ni:afi-safis/" +
    "oc-ni:afi-safi/oc-ni:ipv6-unicast" {
      description
        "Add extended annotations for prefix based Loc-RIB for IPv6";

      uses rib-bgp-ext-ipv6-loc-rib-prefix-top;
  }

  deviation /oc-ni:network-instances/oc-ni:network-instance/oc-ni:protocols/oc-ni:protocol/oc-ni:bgp/oc-ni:rib/oc-ni:afi-safis/oc-ni:afi-safi/oc-ni:ipv4-unicast/oc-bgprib-ext:loc-rib-prefix/oc-bgprib-ext:routes/oc-bgprib-ext:route/oc-bgprib-ext:loc-rib-prefix-paths/oc-bgprib-ext:paths/oc-bgprib-ext:path/oc-bgprib-ext:attr-sets/oc-bgprib-ext:aigp  {
     deviate not-supported;
  }

  deviation /oc-ni:network-instances/oc-ni:network-instance/oc-ni:protocols/oc-ni:protocol/oc-ni:bgp/oc-ni:rib/oc-ni:afi-safis/oc-ni:afi-safi/oc-ni:ipv4-unicast/oc-bgprib-ext:loc-rib-prefix/oc-bgprib-ext:routes/oc-bgprib-ext:route/oc-bgprib-ext:loc-rib-prefix-paths/oc-bgprib-ext:paths/oc-bgprib-ext:path/oc-bgprib-ext:attr-sets/oc-bgprib-ext:aggregator/oc-bgprib-ext:state/oc-bgprib-ext:as4  {
     deviate not-supported;
  }

  deviation /oc-ni:network-instances/oc-ni:network-instance/oc-ni:protocols/oc-ni:protocol/oc-ni:bgp/oc-ni:rib/oc-ni:afi-safis/oc-ni:afi-safi/oc-ni:ipv4-unicast/oc-bgprib-ext:loc-rib-prefix/oc-bgprib-ext:routes/oc-bgprib-ext:route/oc-bgprib-ext:loc-rib-prefix-paths/oc-bgprib-ext:paths/oc-bgprib-ext:path/oc-bgprib-ext:attr-sets/oc-bgprib-ext:as4-path  {
     deviate not-supported;
  }

  deviation /oc-ni:network-instances/oc-ni:network-instance/oc-ni:protocols/oc-ni:protocol/oc-ni:bgp/oc-ni:rib/oc-ni:afi-safis/oc-ni:afi-safi/oc-ni:ipv6-unicast/oc-bgprib-ext:loc-rib-prefix/oc-bgprib-ext:routes/oc-bgprib-ext:route/oc-bgprib-ext:loc-rib-prefix-paths/oc-bgprib-ext:paths/oc-bgprib-ext:path/oc-bgprib-ext:attr-sets/oc-bgprib-ext:aigp  {
     deviate not-supported;
  }

  deviation /oc-ni:network-instances/oc-ni:network-instance/oc-ni:protocols/oc-ni:protocol/oc-ni:bgp/oc-ni:rib/oc-ni:afi-safis/oc-ni:afi-safi/oc-ni:ipv6-unicast/oc-bgprib-ext:loc-rib-prefix/oc-bgprib-ext:routes/oc-bgprib-ext:route/oc-bgprib-ext:loc-rib-prefix-paths/oc-bgprib-ext:paths/oc-bgprib-ext:path/oc-bgprib-ext:attr-sets/oc-bgprib-ext:aggregator/oc-bgprib-ext:state/oc-bgprib-ext:as4  {
     deviate not-supported;
  }

  deviation /oc-ni:network-instances/oc-ni:network-instance/oc-ni:protocols/oc-ni:protocol/oc-ni:bgp/oc-ni:rib/oc-ni:afi-safis/oc-ni:afi-safi/oc-ni:ipv6-unicast/oc-bgprib-ext:loc-rib-prefix/oc-bgprib-ext:routes/oc-bgprib-ext:route/oc-bgprib-ext:loc-rib-prefix-paths/oc-bgprib-ext:paths/oc-bgprib-ext:path/oc-bgprib-ext:attr-sets/oc-bgprib-ext:as4-path  {
     deviate not-supported;
  }

  augment "/oc-ni:network-instances/oc-ni:network-instance/" +
    "oc-ni:protocols/oc-ni:protocol/" +
    "oc-ni:bgp/oc-ni:rib/oc-ni:afi-safis/" +
    "oc-ni:afi-safi/oc-bgp-evpn-ext:l2vpn-evpn/oc-bgp-evpn-ext:loc-rib/" +
    "oc-bgp-evpn-ext:routes/oc-bgp-evpn-ext:route/oc-bgp-evpn-ext:state" {
      description
        "Add best-path field to the Loc-RIB for EVPN";

      leaf best-path {
        type boolean;
        description
          "Current path was selected as the best path.";
      }

      leaf weight {
        type uint16;
        description
          "Weight of the path.";
      }
  }

}
