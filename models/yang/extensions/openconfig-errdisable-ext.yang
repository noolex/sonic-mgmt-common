module openconfig-errdisable-ext {

  yang-version "1";

  // namespace
  namespace "http://openconfig.net/yang/errdisable/extension";

  prefix "oc-errdisable-ext";

  import openconfig-extensions { prefix oc-ext; }
  import openconfig-errdisable-types { prefix oc-errdisable-types; }
  import openconfig-interfaces { prefix "oc-if"; }

  organization
      "SONiC";

  contact
      "SONiC";

  description
    "This module defines configuration and operational state data
    for the ERRDISABLE recovery protocol.";

  oc-ext:openconfig-version "0.1.0";

  revision "2020-06-04" {
    description
      "Initial public revision";
    reference "0.1.0";
  }

  // OpenConfig specific extensions for module metadata.
  oc-ext:regexp-posix;
  oc-ext:catalog-organization "openconfig";
  oc-ext:origin "openconfig";

  // identity statements


  // grouping statements


  grouping errdisable-ext-link-flap-config {

    description
      "Groups ErrDisable Link-flap configurations ";

        	leaf error-disable {
            	type string;
				description
                	"On or off error disable";
			}
        	leaf flap-threshold {
            	type uint8 {
                	range 1..50;
            	}
            	description
                	"This interval is the number of times that the port’s
                	link state goes from up to down and down to up
                	before the recovery-timeout is activated";
        	}

        	leaf sampling-interval {
            	type uint32 {
                	range 1..65535;
            	}
            	description
                	"This time period is the amount of time during which
                	the specified flap-threshold can be crossed. If the flap-threshold
                	is crossed during this sampling-time, port will be error-disabled.";
        	}

        	leaf recovery-interval {
            	type uint32 {
                	range 0..65534;
            	}
            	description
                	"This period of time is the amount of time the port remains disabled
                 	(down) before it becomes enabled. Entering 0 indicates that the
                	port will stay down until an administrative override occurs.";
        	}
		}

  	grouping errdisable-ext-link-flap-state {

    	description
      	"Groups ErrDisable Link-flap state ";

    	leaf status {
          	type string;
			description
            	"The current error disable status";
		}

   		leaf time-left {
            type uint32 {
                range 1..65535;
            }
       		description
       			"Time left for the error disable recovery in seconds.";
   		}
	}

  grouping errdisable-ext-config {
    description
      "Groups ErrDisable Recovery commands ";

    leaf interval {
        type uint32;
        default 300;
        description
            "Interval after which errdisabled ports will be recovered";
    }

    leaf-list cause {
        type identityref {
          base oc-errdisable-types:ERRDISABLE_RECOVERY_CAUSE;
        }
        description
            "Enable/Disable ErrDisable Recovery for a specific cause";
    }
  }

  grouping errdisable-ext-top {
    description
      "Top-level grouping for ERRDISABLE model";

    container errdisable {
      description
        "Top-level container for ERRDISABLE configuration and state data";

      container config {
        description
          "Configuration data ";

        uses errdisable-ext-config;
      }

      container state {

        config false;

        description
          "Operational state data for ERRDISABLE";

        uses errdisable-ext-config;
      }
	}

    container errdisable-port {
		description
      		"Error disable port ";
    	list port {

        	key "name";
                leaf name {
                    type leafref {
                        path "../config/name";
                    }
                    description
                      "Interface name for the port";
                }

    		container config {
        		description
          			"Configuration data for port error-disable";

        		leaf name {
            		type leafref {
                		path "/oc-if:interfaces/oc-if:interface/oc-if:name";
            		}
            		description
                		"Reference to a interface name.";
        		}
			}
    		container state {
        		
				config false;

        		description
          			"State data for port error-disable";

        		leaf name {
            		type leafref {
                		path "/oc-if:interfaces/oc-if:interface/oc-if:name";
            		}
            		description
                		"Reference to a interface name.";
        		}
			}

			container link-flap {

    			container config {
        			description
          				"Configuration data for link-flap error-disable";

          			uses errdisable-ext-link-flap-config;
				}

      			container state {

        			config false;

          			description
            			"The list of link-flap error disable state.";

          			uses errdisable-ext-link-flap-config;
          			uses errdisable-ext-link-flap-state;
        		}
        		description
					"Link-flap error-disable related related data";
			}
    		description
        		"List of ERRDISABLE configuration and state data for ports";
		}

	}

  }
  // data definition statements

  uses errdisable-ext-top;

}
