module openconfig-system-ext {

    yang-version "1";

    namespace "http://openconfig.net/yang/system/extension";

    prefix "oc-sys-ext";

    import openconfig-network-instance { prefix oc-ni; }
    import openconfig-system { prefix oc-sys; }
    import openconfig-inet-types { prefix inet; }
    import openconfig-kdump { prefix oc-kdump; }
    import openconfig-switch-resource { prefix oc-swresource; }
    import openconfig-interfaces { prefix "oc-if"; }
    import openconfig-infra { prefix "oc-infra"; }
    import openconfig-tpcm { prefix "oc-tpcm"; }
    import openconfig-systemd-coredump { prefix oc-systemd-coredump; }
    import openconfig-extensions { prefix "oc-ext"; }
    import sonic-codegen { prefix sonic-codegen; }

    // meta
    organization "OpenConfig working group";

    oc-ext:openconfig-version "0.10.0";

    contact
        "OpenConfig working group
        netopenconfig@googlegroups.com";

    description
        "Model for managing TACACS+ configurations .";

    revision 2020-12-07 {
        description
            "Add per NTP server minpoll and maxpoll.";
        reference "0.12.0";
    }

    revision 2020-11-02 {
        description
            "Add NTP authentication.";
        reference "0.11.0";
    }

    revision 2020-09-02 {
        description
            "Added the VRF name for DNS nameserver.";
        reference "0.10.0";
    }

    revision 2020-06-29 {
        description
            "Fixed a few OC-Yang Lint/Conventions.";
        reference "0.9.0";
    }

    revision 2020-06-10 {
        description
            "Add augments and deviations for NTP.";
        reference "0.8.0";
    }

    revision 2020-06-02 {
        description
            "Moved RADIUS extensions to separate file.";
        reference "0.4.0";
    }

    revision 2020-05-02 {
        description
            "Added DNS source IP support and allowed domain name as well for Radius/TACACS+ server configuration.";
         reference "0.7.0";
    }

    revision 2020-03-30 {
        description
            "Added NAS-IP|IPV6-Address attribute for RADIUS.";
        reference "0.2.0";
    }

    revision 2019-11-05 {
        description
            "Initial augment file.";
         reference "0.7.0";
    }

    // grouping statements

    grouping system-ext-aaa-authentication-config {
        description "Grouping extensions for Authentication configuration";
        leaf failthrough {
            type string;
            description "Should authentication failthrough be enabled/disabled";
        }
    }

    grouping system-ext-aaa-server-group-server-config {
        description "Grouping extensions for AAA server config";
        leaf  auth-type {
            type string;
            description "The server authentication type pap/chap/mschap/mschapv2";
        }
        leaf  priority {
            type uint16;
            description "The server priority";
        }
        leaf vrf {
            type string;
            description "The server's VRF";
        }
    }

    // augment statements

    augment /oc-sys:system {
        description "Kernel dump information";
        uses oc-kdump:kdump-top;
    }

    augment /oc-sys:system {
        description "Coredump information";
        uses oc-systemd-coredump:systemd-coredump-top;
    }

    augment /oc-sys:system {
        description "Switch Resources Management";
        uses oc-swresource:switch-resource-top;
    }

    augment "/oc-sys:system/oc-sys:aaa/oc-sys:authentication/oc-sys:config" {
        description "Additional fields for Authentication configuration";
        uses system-ext-aaa-authentication-config;
    }

    augment "/oc-sys:system/oc-sys:aaa/oc-sys:authentication/oc-sys:state" {
        description "Additional fields for Authentication state data";
        uses system-ext-aaa-authentication-config;
    }

    augment "/oc-sys:system/oc-sys:aaa/oc-sys:server-groups/oc-sys:server-group/oc-sys:servers/oc-sys:server/oc-sys:config" {
        description "Additional fields for AAA server config";
        uses system-ext-aaa-server-group-server-config;
    }

    augment "/oc-sys:system/oc-sys:aaa/oc-sys:server-groups/oc-sys:server-group/oc-sys:servers/oc-sys:server/oc-sys:state" {
        description "Additional fields for AAA server state data";
        uses system-ext-aaa-server-group-server-config;
    }

    grouping system-ext-aaa-server-groups-config {
        description "AAA server group";
        leaf  source-address {
            type inet:ip-address;
            description "The global source ip";
        }
        leaf  auth-type {
            type string;
            default "pap";
            description "The global authentication type pap/chap/mschap/mschapv2";
        }
        leaf  secret-key {
            type string;
            description "The global authentication passkey";
        }
        leaf  timeout {
            type uint16;
            default 5;
            description "The global authentication timeout";
        }
        leaf source-interface {
            type leafref {
                path "/oc-if:interfaces/oc-if:interface/oc-if:name";
            }
            description
                "Source interface to pick the source IP address for the packets to TACACS+ servers";
        }

        leaf encrypted {
            type boolean;
            default false;
            description
                "Secret-key is encrypted";
        }
    }

    augment "/oc-sys:system/oc-sys:aaa/oc-sys:server-groups/oc-sys:server-group/oc-sys:config" {
        description "Additional fields for server-group config";
        uses system-ext-aaa-server-groups-config;
    }

    augment "/oc-sys:system/oc-sys:aaa/oc-sys:server-groups/oc-sys:server-group/oc-sys:state" {
        description "Additional fields for server-group state";
        uses system-ext-aaa-server-groups-config;
    }

    grouping system-ext-ssh-vrf-config {
      description
       "Configuration data for ssh server vrf";
        leaf vrf-name {
            type string {
                pattern "mgmt|Vrf[a-zA-Z0-9_-]+" {
                    error-message "Invalid VRF name for SSH server";
                    error-app-tag vrf-name-ssh-invalid;
                }
            }
            description
                "VRF name";
        }
        leaf port {
            type uint16;
            default 22;
            description
                "SSH port number";
        }
    }

    augment "/oc-sys:system/oc-sys:ssh-server" {
        description "Additional fields for ssh server";
        container ssh-server-vrfs {
          description
           "Container for ssh server vrfs";
            list ssh-server-vrf {
                key "vrf-name";
                max-elements 15;
                description
                  "list of ssh server vrf";

                leaf vrf-name {
                    type leafref {
                        path "../config/vrf-name";
                    }
                    description "VRF name";
                }

                container config {
                    description
                      "Configuration data for ssh server vrf";
                    uses system-ext-ssh-vrf-config;
                }
                container state {
                    config false;
                    description
                      "Operational state data for ssh server vrf";
                    uses system-ext-ssh-vrf-config;
                }
            }
        }
    }

    grouping system-ext-dns-source-config {
        description "Grouping for DNS configuration";
        leaf source-interface {
            type leafref {
                path "/oc-if:interfaces/oc-if:interface/oc-if:name";
            }
            description
                "Source interface to pick the source IP address for the packets to DNS name server";
        }
    }

    grouping system-ext-dns-server-config {
        description "Grouping for DNS server configuration";
        leaf vrf-name {
            type leafref {
                path "/oc-ni:network-instances/oc-ni:network-instance/oc-ni:name";
            }
            description
                "VRF name";
        }
    }

    augment "/oc-sys:system/oc-sys:dns/oc-sys:config" {
        description "Additional fields for DNS config";
        uses system-ext-dns-source-config;
    }

    augment "/oc-sys:system/oc-sys:dns/oc-sys:state" {
        description "Additional fields for DNS state";
        uses system-ext-dns-source-config;
    }

    augment "/oc-sys:system/oc-sys:dns/oc-sys:servers/oc-sys:server/oc-sys:config" {
        description "Additional fields for DNS server config";
        uses system-ext-dns-server-config;
    }

    augment "/oc-sys:system/oc-sys:dns/oc-sys:servers/oc-sys:server/oc-sys:state" {
        description "Additional fields for DNS server state";
        uses system-ext-dns-server-config;
    }


    typedef server-address {
        type inet:host;
        description
            "The host type represents either an unzoned IP address or a DNS
            domain name.";
    }

    deviation "/oc-sys:system/oc-sys:aaa/oc-sys:server-groups/oc-sys:server-group/oc-sys:servers/oc-sys:server/oc-sys:config/oc-sys:address" {
        sonic-codegen:lint-ignore "Deviated to support both IPaddr or DNS name";
        deviate replace {
            type server-address;
        }
    }

    deviation "/oc-sys:system/oc-sys:aaa/oc-sys:server-groups/oc-sys:server-group/oc-sys:servers/oc-sys:server/oc-sys:state/oc-sys:address" {
        sonic-codegen:lint-ignore "Deviated to support both IPaddr or DNS name";
        deviate replace {
            type server-address;
        }
    }

    deviation /oc-sys:system/oc-sys:config/oc-sys:domain-name {
       deviate not-supported;
    }

    deviation /oc-sys:system/oc-sys:config/oc-sys:hostname{
	sonic-codegen:lint-ignore "Deviated to be aligned with klish.";
	deviate replace {
	    type string {
                pattern "^([a-zA-Z0-9]|[a-zA-Z0-9][a-zA-Z0-9\-]{0,61}[a-zA-Z0-9])(\.([a-zA-Z0-9]|[a-zA-Z0-9][a-zA-Z0-9\-]{0,61}[a-zA-Z0-9]))*$" {
		    error-message "Invalid hostname";
		} 
		
	    }
        }
    }


    deviation /oc-sys:system/oc-sys:config/oc-sys:login-banner {
        deviate not-supported;
    }

    deviation /oc-sys:system/oc-sys:config/oc-sys:motd-banner {
        deviate not-supported;
    }

	// ssh-server deviations.

    deviation /oc-sys:system/oc-sys:ssh-server/oc-sys:config {
       deviate not-supported;
    }
    deviation /oc-sys:system/oc-sys:ssh-server/oc-sys:state {
       deviate not-supported;
    }

	//syslog parameters
    grouping system-ext-logging-remote-config {
        description 
			"Grouping for remote server source-interface and vrf configuration";
        leaf source-interface {
            type leafref {
                path "/oc-if:interfaces/oc-if:interface/oc-if:name";
            }
            description
                "Source interface ip to be used as source ip for sending syslog packets";
        }
        leaf vrf-name {
            type leafref {
                path "/oc-ni:network-instances/oc-ni:network-instance/oc-ni:name";
            }
            description
                "VRF name";
        }
    }

    augment "/oc-sys:system/oc-sys:logging/oc-sys:remote-servers/oc-sys:remote-server/oc-sys:config" {
        description "Additional parameters for remote server config";
        uses system-ext-logging-remote-config;
	}
    augment "/oc-sys:system/oc-sys:logging/oc-sys:remote-servers/oc-sys:remote-server/oc-sys:state" {
        description "Additional parameters for remote server state";
        uses system-ext-logging-remote-config;
	}
    deviation /oc-sys:system/oc-sys:logging/oc-sys:remote-servers/oc-sys:remote-server/oc-sys:selectors {
       deviate not-supported;
    }
    deviation /oc-sys:system/oc-sys:logging/oc-sys:remote-servers/oc-sys:remote-server/oc-sys:config/oc-sys:source-address {
        deviate not-supported;
	}
    deviation /oc-sys:system/oc-sys:logging/oc-sys:remote-servers/oc-sys:remote-server/oc-sys:state/oc-sys:source-address {
        deviate not-supported;
	}

    //infra paraemters
    augment /oc-sys:system {
        description "System infra";
        uses oc-infra:infra-top;
    }

   //tpcm paraemters
    augment /oc-sys:system {
        description "Additional fields TPCM";
        uses oc-tpcm:tpcm-top;
    }

  rpc tpcm-install {
    description
      "Install the TPC image into SONiC system";
    input {
      leaf docker-name{
        type string;
        description
          "docker name for the TPC image to be installed";
      }
      leaf image-source{
        type string;
        description
          "image download source: url, image, pull, file, scp, sftp";
      }
      leaf image-name{
        type string;
        description
          "image name for the TPC container to be installed";
      }
      leaf remote-server {
        type string;
        description
          "the remote server name for scp and sftp";
      }
      leaf username{
        type string;
        description
          "the remote server login username";
      }
      leaf password{
        type string;
        description
          "the remote server login password";
      }
      leaf args {
        type string;
        description
          "additional startup args to the container";
      }
    }
    output {
      leaf status {
        type int32;
        description
          "The status of the operation execution request.";
      }
      leaf-list status-detail {
            type string;
            description "The detailed status of the operation execution request.";
      }
    }
  }

  rpc tpcm-uninstall{
    description
      "Uninstall the TPC image from SONiC system";
    input {
      leaf clean-data {
        type string;
        description
          "Delete the TPC data: yes or no";
      }
     leaf docker-name{
        type string;
        description
          "docker name for the TPC image to be uninstalled";
      }
    }
    output {
      leaf status {
        type int32;
        description
          "The status of the operation execution request.";
      }
      leaf-list status-detail {
            type string;
            description "The detailed status of the operation execution request.";
      }
   }
  }


  rpc tpcm-upgrade{
    description
      "Upgrade the existing TPC container";
    input {
     leaf docker-name{
        type string;
        description
          "docker name for the TPC image to be upgraded";
      }
      leaf image-source{
        type string;
        description
          "image download source: url, image, pull, file, scp, sftp";
      }
      leaf image-name{
        type string;
        description
          "image name for the TPC container to be upgraded";
      }
      leaf remote-server {
        type string;
        description
          "the remote server name for scp and sftp";
      }
      leaf username{
        type string;
        description
          "the remote server login username";
      }
      leaf password{
        type string;
        description
          "the remote server login password";
      }
      leaf skip-data-migration {
        type string;
        description
          "skip the TPC data migration: yes or no";
      }
      leaf args {
        type string;
        description
          "additional startup args to the container";
      }

    }
    output {
      leaf status {
        type int32;
        description
          "The status of the operation execution request.";
      }
      leaf-list status-detail {
            type string;
            description
               "The detailed status of the operation execution request.";
      }

   }
 }
    rpc show-sys-log {
        description
            "show system log";
        input {
            leaf num-lines{
                type uint16{
                    range "1..65535" {
                        error-message "NUM Lines out of range 1..65535";
                    }
                }
               description
                    "output the last NUM lines of system log";
            }
        }

        output {
            leaf-list status-detail{
               type string;
               description
                    "The detailed status of the operation execution request.";
           }
        }
    }

    rpc clear-sys-log {
        description
            "clear logging";
        output {
            leaf result{
               type string;
               description
                    "The detailed status of the operation execution request.";
           }
        }
    }

    rpc reboot-ops{
        description
            "Switch boot operations:
                - reboot: reboot operation
                - warm-reboot : warm reboot  operation
                - fast-reboot : fast reboot operation
            The result of the requested command is sent as a string.";
        input {
            leaf param {
                type string {
                    pattern "reboot warm-reboot fast-reboot";
                }
               description
                    "reboot options";
            }
        }
        output {
            leaf result {
                type string;
                description
                    "String showing the result of the last requested command (reboot, warm-reboot or fast-reboot).";
            }
        }
    }

    rpc sys-log-count {
        description
            "total number of system log entries";
        output {
            leaf result{
               type string;
               description
                    "total number of system log entries";
           }
        }
    }
    rpc set-loglevel-severity {
        description
            "logging severity level setting";
        input {
            leaf loglevel{
                type string; 
                description
                    "loglevel value";
            }
            leaf component-name {
                type string; 
                description
                    "component name in DB for which loglevel is applied (provided with loglevel): component name or all";
            }
            leaf sai-component {
                type boolean; 
                default false;
                description
                    "apply loglevel for SAI api component";
            }
        }
        output {
            leaf-list status-detail{
               type string;
               description
                    "The detailed status of the operation execution request.";
           }
        }
    }
    rpc get-loglevel-severity {
        description
           "print components registered in DB for which setting can be applied";
        output {
            leaf-list status-detail{
               type string;
               description
                    "The detailed status of the operation execution request.";
           }
        }
    }
    rpc show-sys-in-memory-log {
        description
            "show system inmemory log";
        input {
            leaf num-lines{
                type uint16{
                    range "1..65535" {
                        error-message "NUM Lines out of range 1..65535";
                    }
                }
               description
                    "output the last NUM lines of system inmemory log";
            }
        }

        output {
            leaf-list status-detail{
               type string;
               description
                    "The detailed status of the operation execution request.";
           }
        }
    }
    rpc sys-in-memory-log-count {
        description
            "total number of system inmemory log entries";
        output {
            leaf result{
               type string;
               description
                    "total number of system inmemory log entries";
           }
        }
    }

    rpc locator-led-chassis-on {
        description
            "Enable Locator Chassis LED";
        output {
            leaf result {
               type string;
               description
                    "The detailed status of the operation execution request.";
           }
        }
    }
    rpc locator-led-chassis-off {
        description
            "Disable Locator Chassis LED";
        output {
            leaf status{
               type string;
               description
                    "The detailed status of the operation execution request.";
           }
        }
    }
    rpc show-locator-led-chassis {
        description
            "Show Locator Chassis LED State";
        output {
            leaf-list status-detail{
               type string;
               description
                    "The detailed status of the operation execution request.";
           }
        }
    }
   rpc logger {
        description
            "enter messages into the system log";
        input {
            leaf messages {
               type string; 
               description
                    "messages into the system log";
            }
        }

        output {
            leaf result{
               type string;
               description
                    "The detailed status of the operation execution request.";
           }
        }
    }
}
