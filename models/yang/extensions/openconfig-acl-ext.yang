module openconfig-acl-ext {

    yang-version "1";

    namespace "http://openconfig.net/yang/acl/extension";

    prefix "oc-acl-ext";

    import openconfig-packet-match-types { prefix oc-pkt-match-types; }
    import openconfig-acl { prefix oc-acl; }
    import openconfig-extensions { prefix oc-ext; }

    // meta
    organization "SONiC";

    contact
        "SONiC
        https://github.com/Azure/SONiC";

    description
        "This model describes the acl extensions.";

    oc-ext:openconfig-version "0.1.0";

    revision 2020-02-08 {
        description
            "Initial augment file.";

        reference "0.1.0";
    }

    // augment statements
    identity TRANSIT {
        base oc-acl:FORWARDING_ACTION;
        description
            "Allow the packet to be forwarded. Do not allow the packets to be trapped to CPU.";
    }

    identity DISCARD {
        base oc-acl:FORWARDING_ACTION;
        description
            "Drop packet without sending any ICMP error message. Do not allow the packets to be trapped to CPU.";
    }

    identity DO_NOT_NAT {
       base oc-acl:FORWARDING_ACTION;
       description
         "Do not do NAT on the incoming packet";
    }

    grouping acl-ext-ethernet-header-config {
        description
            "Grouping for Layer 2 header extension fields";

        leaf pcp {
            type uint8 {
                range "0..7";
            }
            description "IEEE 802 Priority Code Point";
        }
        leaf pcp-mask {
            type uint8 {
                range "0..7";
            }
            description "IEEE 802 Priority Code Point";
        }
        leaf dei {
            type uint8 {
                range "0..1";
            }
            description "IEEE 802 Drop Eligible Indicator";
        }
        leaf vlanid {
            type uint16 {
                range "1..4094";
            }
            description "VLAN ID";
        }
    }

    grouping "acl-ext-transport-fields-config" {
        description
            "Grouping for ICMP header fields";

        leaf icmp-type {
            type uint8;
            description "ICMP or ICMPv6 Type";
        }
        leaf icmp-code {
            type uint8;
            description "ICMP or ICMPv6 Code";
        }

        leaf tcp-session-established {
            type boolean;
            description
                "Match the traffic which is part of TCP session which is established.
                Match on TCP flags may not be be allowed if this configuration is 
                used";
        }
    }

    augment "/oc-acl:acl/oc-acl:acl-sets/oc-acl:acl-set/oc-acl:acl-entries/oc-acl:acl-entry/oc-acl:l2/oc-acl:config" {
        description
            "Augmentation to support configuration of additional Layer2 header fields";

        uses acl-ext-ethernet-header-config;
    }

    augment "/oc-acl:acl/oc-acl:acl-sets/oc-acl:acl-set/oc-acl:acl-entries/oc-acl:acl-entry/oc-acl:l2/oc-acl:state" {
        description
            "Augmentation to support operational state of additional Layer2 header fields";

        uses acl-ext-ethernet-header-config;
    }
    
    augment "/oc-acl:acl/oc-acl:acl-sets/oc-acl:acl-set/oc-acl:acl-entries/oc-acl:acl-entry/oc-acl:transport/oc-acl:config" {
        description
            "Augmentation to support configuration of additional TCP header fields";

        uses acl-ext-transport-fields-config;
    }

    augment "/oc-acl:acl/oc-acl:acl-sets/oc-acl:acl-set/oc-acl:acl-entries/oc-acl:acl-entry/oc-acl:transport/oc-acl:state" {
        description
            "Augmentation to support operational state of additional TCP header fields";

        uses acl-ext-transport-fields-config;
    }

    grouping acl-ext-config {
        description
            "Global configuration data for ACLs";

        leaf counter-capability {
            type identityref {
                base oc-acl:ACL_COUNTER_CAPABILITY;
            }

            description
                "System reported indication of how ACL counters are reported by the target";
        }
    }

    augment /oc-acl:acl/oc-acl:config {
        description
            "Augmentation to support configuration of counter capability";

        uses acl-ext-config;
    }

    typedef ip-protocol-type-ext {
        type union {
            type uint8;
            type identityref {
                base oc-pkt-match-types:IP_PROTOCOL;
            }
        }

        description
            "The IP protocol number may be expressed as a valid protocol
            number (integer) or using a protocol type defined by the
            IP_PROTOCOL identity";
    }

    deviation /oc-acl:acl/oc-acl:acl-sets/oc-acl:acl-set/oc-acl:acl-entries/oc-acl:acl-entry/oc-acl:ipv4/oc-acl:config/oc-acl:protocol {
        deviate replace {
            type ip-protocol-type-ext;
        }
    }
    deviation /oc-acl:acl/oc-acl:acl-sets/oc-acl:acl-set/oc-acl:acl-entries/oc-acl:acl-entry/oc-acl:ipv4/oc-acl:state/oc-acl:protocol {
        deviate replace {
            type ip-protocol-type-ext;
        }
    }
    deviation /oc-acl:acl/oc-acl:acl-sets/oc-acl:acl-set/oc-acl:acl-entries/oc-acl:acl-entry/oc-acl:ipv6/oc-acl:config/oc-acl:protocol {
        deviate replace {
            type ip-protocol-type-ext;
        }
    }
    deviation /oc-acl:acl/oc-acl:acl-sets/oc-acl:acl-set/oc-acl:acl-entries/oc-acl:acl-entry/oc-acl:ipv6/oc-acl:state/oc-acl:protocol {
        deviate replace {
            type ip-protocol-type-ext;
        }
    }
	deviation /oc-acl:acl/oc-acl:acl-sets/oc-acl:acl-set/oc-acl:acl-entries/oc-acl:acl-entry/oc-acl:ipv4/oc-acl:config/oc-acl:hop-limit {
		deviate not-supported;
	}
	deviation /oc-acl:acl/oc-acl:acl-sets/oc-acl:acl-set/oc-acl:acl-entries/oc-acl:acl-entry/oc-acl:ipv4/oc-acl:state/oc-acl:hop-limit {
		deviate not-supported;
	}
	deviation /oc-acl:acl/oc-acl:acl-sets/oc-acl:acl-set/oc-acl:acl-entries/oc-acl:acl-entry/oc-acl:ipv6/oc-acl:config/oc-acl:source-flow-label {
		deviate not-supported;
	}
	deviation /oc-acl:acl/oc-acl:acl-sets/oc-acl:acl-set/oc-acl:acl-entries/oc-acl:acl-entry/oc-acl:ipv6/oc-acl:config/oc-acl:destination-flow-label {
		deviate not-supported;
	}
	deviation /oc-acl:acl/oc-acl:acl-sets/oc-acl:acl-set/oc-acl:acl-entries/oc-acl:acl-entry/oc-acl:ipv6/oc-acl:config/oc-acl:hop-limit {
		deviate not-supported;
	}
	deviation /oc-acl:acl/oc-acl:acl-sets/oc-acl:acl-set/oc-acl:acl-entries/oc-acl:acl-entry/oc-acl:ipv6/oc-acl:state/oc-acl:source-flow-label {
		deviate not-supported;
	}
	deviation /oc-acl:acl/oc-acl:acl-sets/oc-acl:acl-set/oc-acl:acl-entries/oc-acl:acl-entry/oc-acl:ipv6/oc-acl:state/oc-acl:destination-flow-label {
		deviate not-supported;
	}
	deviation /oc-acl:acl/oc-acl:acl-sets/oc-acl:acl-set/oc-acl:acl-entries/oc-acl:acl-entry/oc-acl:ipv6/oc-acl:state/oc-acl:hop-limit {
		deviate not-supported;
	}
	deviation /oc-acl:acl/oc-acl:acl-sets/oc-acl:acl-set/oc-acl:acl-entries/oc-acl:acl-entry/oc-acl:input-interface {
		deviate not-supported;
	}
	deviation /oc-acl:acl/oc-acl:acl-sets/oc-acl:acl-set/oc-acl:acl-entries/oc-acl:acl-entry/oc-acl:actions/oc-acl:config/oc-acl:log-action {
		deviate not-supported;
	}
	deviation /oc-acl:acl/oc-acl:acl-sets/oc-acl:acl-set/oc-acl:acl-entries/oc-acl:acl-entry/oc-acl:actions/oc-acl:state/oc-acl:log-action {
		deviate not-supported;
	}
    deviation /oc-acl:acl/oc-acl:interfaces/oc-acl:interface/oc-acl:interface-ref/oc-acl:config/oc-acl:subinterface  {
        deviate not-supported;
    }
    deviation /oc-acl:acl/oc-acl:interfaces/oc-acl:interface/oc-acl:interface-ref/oc-acl:state/oc-acl:subinterface {
        deviate not-supported;
    }

    grouping acl-ext-global-acl-entries-config {
        description
            "Configuration data global ACLs";
    }

    grouping acl-ext-global-acl-entries-state {
        description
            "Operational state data for global ACL entries";

        leaf sequence-id {
            type leafref {
                path "/oc-acl:acl/oc-acl:acl-sets/" +
                    "oc-acl:acl-set[oc-acl:name=current()/../../../../set-name]" +
                    "[oc-acl:type=current()/../../../../type]/" +
                    "oc-acl:acl-entries/oc-acl:acl-entry/oc-acl:sequence-id";
            }

            description
                "Reference to an entry in the ACL set applied globally";
        }

        uses oc-acl:acl-counters-state;
    }

    grouping acl-ext-global-acl-entries-top {
        description
            "Top-level grouping for global ACL entries";

        container acl-entries {
            config false;
            description
                "Enclosing container for list of references to ACLs";

            list acl-entry {
                key "sequence-id";
                description
                    "List of ACL entries assigned globally";

                leaf sequence-id {
                    type leafref {
                        path "../state/sequence-id";
                    }
                    description
                        "Reference to global acl entry key";
                }

                // no config container since the enclosing container is
                // read-only

                container state {
                    config false;

                    description
                        "Operational state data for global ACL entries";

                    uses acl-ext-global-acl-entries-config;
                    uses acl-ext-global-acl-entries-state;
                }
            }
        }
    }

    grouping acl-ext-global-ingress-acl-config {
        description
            "Configuration data for global ingress ACLs";

        leaf set-name {
            type leafref {
                path "/oc-acl:acl/oc-acl:acl-sets/oc-acl:acl-set/oc-acl:config/oc-acl:name";
            }
            description
                "Reference to the ACL set name applied on ingress";
        }

        leaf type {
            type leafref {
                path "/oc-acl:acl/oc-acl:acl-sets/oc-acl:acl-set[oc-acl:name=current()/../set-name]" +
                    "/oc-acl:config/oc-acl:type";
            }
            description
                "Reference to the ACL set type applied on ingress";
        }
    }

    grouping acl-ext-global-ingress-acl-state {
        description
            "Operational state data for global ingress ACL";
    }

    grouping acl-ext-global-ingress-acl-top {
        description
            "Top-level grouping for global ingress ACL data";

        container ingress-acl-sets {
            description
                "Enclosing container the list of ingress ACLs globally";

            list ingress-acl-set {
                key "set-name type";
                description
                    "List of ingress ACLs";

                leaf set-name {
                    type leafref {
                        path "../config/set-name";
                    }
                    description
                        "Reference to set name list key";
                }

                leaf type {
                    type leafref {
                        path "../config/type";
                    }
                    description
                        "Reference to type list key";
                }

                container config {
                    description
                        "Configuration data ";

                    uses acl-ext-global-ingress-acl-config;
                }

                container state {
                    config false;

                    description
                        "Operational state data for global ingress ACLs";

                    uses acl-ext-global-ingress-acl-config;
                    uses acl-ext-global-ingress-acl-state;
                }

                uses acl-ext-global-acl-entries-top;
            }
        }
    }

    grouping acl-ext-global-egress-acl-config {
        description
            "Configuration data for global egress ACLs";

        leaf set-name {
            type leafref {
                path "/oc-acl:acl/oc-acl:acl-sets/oc-acl:acl-set/oc-acl:config/oc-acl:name";
            }
            description
                "Reference to the ACL set name applied on egress";
        }

        leaf type {
            type leafref {
                path "/oc-acl:acl/oc-acl:acl-sets/oc-acl:acl-set[oc-acl:name=current()/../set-name]" +
                    "/oc-acl:config/oc-acl:type";
            }
            description
                "Reference to the ACL set type applied on egress";
        }
    }

    grouping acl-ext-global-egress-acl-state {
        description
            "Operational state data for global egress ACL";
    }

    grouping acl-ext-global-egress-acl-top {
        description
            "Top-level grouping for global egress ACL data";

        container egress-acl-sets {
            description
                "Enclosing container the list of egress ACLs globally";

            list egress-acl-set {
                key "set-name type";
                description
                    "List of egress ACLs";

                leaf set-name {
                    type leafref {
                        path "../config/set-name";
                    }
                    description
                        "Reference to set name list key";
                }

                leaf type {
                    type leafref {
                        path "../config/type";
                    }
                    description
                        "Reference to type list key";
                }

                container config {
                    description
                        "Configuration data ";

                    uses acl-ext-global-egress-acl-config;
                }

                container state {
                    config false;

                    description
                        "Operational state data for global egress ACLs";

                    uses acl-ext-global-egress-acl-config;
                    uses acl-ext-global-egress-acl-state;
                }

                uses acl-ext-global-acl-entries-top;
            }
        }
    }

    grouping acl-ext-global-acl-top {
        description
            "Top-level grouping for Global ACL data";

        container config {
            description
                "Configuration for ACL per-interface data";
        }

        container state {
            config false;

            description
                "Operational state for ACL per-interface data";
        }

        uses acl-ext-global-ingress-acl-top;
        uses acl-ext-global-egress-acl-top;
    }

    grouping acl-ext-ctrl-plane-ingress-acl-config {
        description
            "Configuration data for control plane ingress ACLs";

        leaf set-name {
            type leafref {
                path "/oc-acl:acl/oc-acl:acl-sets/oc-acl:acl-set/oc-acl:config/oc-acl:name";
            }
            description
                "Reference to the ACL set name applied on ingress";
        }

        leaf type {
            type identityref {
                base oc-acl:ACL_TYPE;
            }   
            description
                "Reference to the ACL set type applied on ingress";
        }
    }

    grouping acl-ext-ctrl-plane-ingress-acl-top {
        description
            "Top-level grouping for control plane ingress ACL data";

        container ingress-acl-sets {
            description
                "Enclosing container the list of ingress control plane ACLs";

            list ingress-acl-set {
                key "set-name type";
                description
                    "List of ingress ACLs";

                leaf set-name {
                    type leafref {
                        path "../config/set-name";
                    }
                    description
                        "Reference to set name list key";
                }

                leaf type {
                    type leafref {
                        path "../config/type";
                    }
                    description
                        "Reference to type list key";
                }

                container config {
                    description
                        "Configuration data ";

                    uses acl-ext-ctrl-plane-ingress-acl-config;
                }

                container state {
                    config false;

                    description
                        "Operational state data";

                    uses acl-ext-ctrl-plane-ingress-acl-config;
                }
            }
        }
    }

    grouping acl-ext-ctrl-plane-acl-top {
        description
            "Top-level grouping for Control Plane ACL data";

        container config {
            description
                "Configuration for ACL per-interface data";
        }

        container state {
            config false;

            description
                "Operational state for ACL per-interface data";
        }

        uses acl-ext-ctrl-plane-ingress-acl-top;
    }

    augment /oc-acl:acl {
        description
            "Augmentation to add support for Global and Control plane ACLs";

        container global {
            description
                "Global ACL application related configuration and operational state";

            uses acl-ext-global-acl-top;
        }

        container control-plane {
            description
                "Control plane ACL related configuration and operational state";

            uses acl-ext-ctrl-plane-acl-top;
        }
    }
}
