module openconfig-aft-ipv4-ext {

  yang-version "1";

  // namespace
  namespace "http://openconfig.net/yang/aft-ipv4/extension";

  prefix "oc-aft-ipv4-ext";

  // import some basic types
  import openconfig-network-instance { prefix oc-netinst; }
  import openconfig-aft-ext { prefix oc-aft-ext; }
  import openconfig-inet-types { prefix oc-inet; }
  import openconfig-extensions { prefix oc-ext; }

  organization
      "SONiC";

  contact
      "SONiC";

  description
    "This module describes a deviation for network instance afts-ipv4
     extensions.";

  oc-ext:openconfig-version "0.1.0";

  revision "2019-11-13" {
    description
      "Network instance aft-ipv4 extensions.";

    reference "0.1.0";
  }

  grouping aft-ipv4-ext-ipv4-multicast-structural-state {
      description
          "Structural grouping defining the schema for the IPv4 multicast abstract forwarding table.";

      container ipv4-entries {
          config false;
          description
              "Details about all IPv4 multicast entries present in forwarding table.";

          list ipv4-entry {
              key "group-address";

              description
                  "List of the IPv4 multicast entries within the abstract forwarding table.
                  This list is keyed by the destination IPv4 multicast group & source address.";

              leaf group-address {
                  type leafref {
                      path "../state/group-address";
                  }
                  description
                      "Reference to the group-address key";
              }

              container state {
                  description "Operational state information.";

                  leaf group-address {
                      type oc-inet:ipv4-address;
                      description
                          "IPv4 Multicast group-address";
                  }

                  container src-entries {
                      description
                          "Details about all multicast-source information of this particular multicast group-address entry.";

                      list src-entry {
                          key "source-address";

                          description
                              "List of different source-address entries within this particular multicast group-address entry.";

                          leaf source-address {
                              type leafref {
                                  path "../state/source-address";
                              }
                              description
                                  "Reference to the source-address key";
                          }

                          container state {
                              description
                                  "Operational state parameters for the IPv4 multicast AFT entry.";

                              leaf source-address {
                                  type oc-inet:ipv4-address;
                                  description
                                      "IPv4 Unicast source-address of the device, which originates this particular multicast group traffic.
                                      This address can be 0.0.0.0 in case of *,G multicast group entry.";
                              }

                              uses oc-aft-ext:aft-ext-common-ip-mcast-entry-state;
                          }
                      }
                  }
              }
          }
      }
  }

  grouping aft-ipv4-ext-ipv4-mcast-top {
        description
            "AFT IPv4 Multicast data.";
      container ipv4-multicast {
          description
              "The abstract forwarding table for IPv4 multicast. Entries
              within this table are uniquely keyed on the IPv4 multicast
              destination prefix which is matched by ingress packets.

              The data set represented by the IPv4 Multicast AFT is the set
              of entries from the IPv4 multicast RIB that have been selected
              for installation into the FIB of the device exporting the
                  data structure.";

          uses aft-ipv4-ext-ipv4-multicast-structural-state;
      }
  }

  augment /oc-netinst:network-instances/oc-netinst:network-instance/oc-netinst:afts {
        description
            "AFT IPv4 Multicast extensions.";
        uses aft-ipv4-ext-ipv4-mcast-top;
  }
}
