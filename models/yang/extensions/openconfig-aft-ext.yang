module openconfig-aft-ext {

    yang-version "1";

    //namespace
    namespace "http://openconfig.net/yang/aft/extension";

    prefix "oc-aft-ext";

    import openconfig-interfaces { prefix oc-if; }
    import openconfig-extensions { prefix oc-ext; }
    import openconfig-types { prefix "oc-types"; }

    organization
        "SONiC";

    contact
        "SONiC";

    description
      "This module describes a common extensions used for afts-ipv4,afts-ipv6";

    oc-ext:openconfig-version "0.1.0";

    revision "2019-11-13" {
      description
        "Network instance aft common extensions.";

      reference "0.1.0";
    }

    grouping aft-ext-common-ip-mcast-entry-state {
        description
            "AFT common IPv4 Multicast data.";

        leaf incoming-interface {
            type oc-if:interface-id;
            description
                "Incoming interface for this multicast entry.";
        }

        leaf installed {
            type boolean;
            description
                "When set to TRUE, it states the multicast entry is installed in HW.";
        }

        container oil-info-entries {
            description
                "Details about all outgoing interfaces of this multicast entry.";

            list oif-info {
                key "outgoing-interface";

                description
                    "Details about outgoing interface for this multicast entry.";

                leaf outgoing-interface {
                    type leafref {
                        path "../state/outgoing-interface";
                    }
                    description
                        "Reference to the outgoing-interface key";
                }

                container state {
                    description
                        "Common Operational state information of an outgoing interface in this multicast entry.";

                    leaf outgoing-interface {
                        type oc-if:interface-id;
                        description
                            "Outgoing interface for this multicast entry.";
                    }

                    leaf uptime {
                        type oc-types:timeticks64;
                        description
                            "This timestamp indicates the time, since this particular outgoing interface is present in this multicast entry.
                            The value is the timestamp in seconds relative to the Unix Epoch (Jan 1, 1970 00:00:00 UTC).
                            It can be computed by clients as the difference between this value and the current time in UTC.";
                    }
                }
            }
        }
    }
}
