module openconfig-local-routing-ext {

  yang-version "1";

  // namespace
  namespace "http://openconfig.net/yang/local-routing/extension";

  prefix "oc-local-routing-ext";

  import openconfig-bfd { prefix oc-bfd; }
  import openconfig-network-instance { prefix oc-netinst; }
  import openconfig-extensions { prefix "oc-ext"; }

  organization
    "OpenConfig working group";

  contact
    "OpenConfig working group
    www.openconfig.net";

  description
        "This module describes a YANG model for local routing
        configuration extensions.";

  oc-ext:openconfig-version "0.2.0";

  revision "2020-08-03" {
    description
      "Add unsupported attribute tag and extensions.";
    reference "0.2.0";
  }

  revision "2020-03-13" {
    description
      "Add OpenConfig unsupported attributes and extensions.";
    reference "0.1.0";
  }

  grouping local-routing-ext-next-hop-ntwk-instance-config {
      description
          "Group for static route next-hop network instance";

      leaf nexthop-network-instance {
          type string;
          description
              "name of the Next-hop network instance for leaked routes";
      }
   }

   grouping local-routing-ext-blackhole-config {
      description
          "Group for static route next-hop blackhole flag";

      leaf blackhole {
         type boolean;
         default false;
         description
              "True if route is blackholed. Only metric is relevant in a blackholed nexthop, no other parameter should be supplied for a nexthop set as blackhole.";
      }

      leaf track {
        type uint16 {
          range "1..255" {
            error-message "Track ID out of range";
          }
        }
        description
          "Ip sla track id for static route";
      }

  }
  
  grouping local-routing-ext-tag-config {
      description
          "Group for static route next-hop tag value";

      leaf tag {
         type uint32;
         description
              "Tag value for the static route. This references the tag set in route map";
      }

  }

  


  deviation /oc-netinst:network-instances/oc-netinst:network-instance/oc-netinst:protocols/oc-netinst:protocol/oc-netinst:static-routes/oc-netinst:static/oc-netinst:config/oc-netinst:set-tag {

      deviate not-supported;
  }

  deviation /oc-netinst:network-instances/oc-netinst:network-instance/oc-netinst:protocols/oc-netinst:protocol/oc-netinst:static-routes/oc-netinst:static/oc-netinst:state/oc-netinst:set-tag {

      deviate not-supported;
  }



  deviation /oc-netinst:network-instances/oc-netinst:network-instance/oc-netinst:protocols/oc-netinst:protocol/oc-netinst:static-routes/oc-netinst:static/oc-netinst:next-hops/oc-netinst:next-hop/oc-netinst:config/oc-netinst:recurse {

      deviate not-supported;
  }

  deviation /oc-netinst:network-instances/oc-netinst:network-instance/oc-netinst:protocols/oc-netinst:protocol/oc-netinst:static-routes/oc-netinst:static/oc-netinst:next-hops/oc-netinst:next-hop/oc-netinst:state/oc-netinst:recurse {

      deviate not-supported;
  }

  deviation /oc-netinst:network-instances/oc-netinst:network-instance/oc-netinst:protocols/oc-netinst:protocol/oc-netinst:static-routes/oc-netinst:static/oc-netinst:next-hops/oc-netinst:next-hop/oc-netinst:interface-ref/oc-netinst:config/oc-netinst:subinterface {

      deviate not-supported;
  }

 deviation /oc-netinst:network-instances/oc-netinst:network-instance/oc-netinst:protocols/oc-netinst:protocol/oc-netinst:static-routes/oc-netinst:static/oc-netinst:next-hops/oc-netinst:next-hop/oc-netinst:interface-ref/oc-netinst:state/oc-netinst:subinterface {

      deviate not-supported;
  }

    deviation /oc-netinst:network-instances/oc-netinst:network-instance/oc-netinst:protocols/oc-netinst:protocol/oc-netinst:static-routes/oc-netinst:static/oc-netinst:next-hops/oc-netinst:next-hop/oc-netinst:enable-bfd {
      deviate not-supported;
    }

  augment "/oc-netinst:network-instances/oc-netinst:network-instance/oc-netinst:protocols/oc-netinst:protocol/oc-netinst:static-routes/oc-netinst:static/oc-netinst:next-hops/oc-netinst:next-hop/oc-netinst:config" {
      description
          "Next hop network instance";
      uses local-routing-ext-next-hop-ntwk-instance-config;
   }
  augment "/oc-netinst:network-instances/oc-netinst:network-instance/oc-netinst:protocols/oc-netinst:protocol/oc-netinst:static-routes/oc-netinst:static/oc-netinst:next-hops/oc-netinst:next-hop/oc-netinst:state" {
      description
          "Next hop network instance";
      uses local-routing-ext-next-hop-ntwk-instance-config;
   }

   augment "/oc-netinst:network-instances/oc-netinst:network-instance/oc-netinst:protocols/oc-netinst:protocol/oc-netinst:static-routes/oc-netinst:static/oc-netinst:next-hops/oc-netinst:next-hop/oc-netinst:config" {
      description
          "Next hop blackhole flag";
      uses local-routing-ext-blackhole-config;
   }

   augment "/oc-netinst:network-instances/oc-netinst:network-instance/oc-netinst:protocols/oc-netinst:protocol/oc-netinst:static-routes/oc-netinst:static/oc-netinst:next-hops/oc-netinst:next-hop/oc-netinst:config" {
      description
          "Next hop tag value";
      uses local-routing-ext-tag-config;
   }

   augment "/oc-netinst:network-instances/oc-netinst:network-instance/oc-netinst:protocols/oc-netinst:protocol/oc-netinst:static-routes/oc-netinst:static/oc-netinst:next-hops/oc-netinst:next-hop/oc-netinst:state" {
      description
          "Next hop blackhole flag";
      uses local-routing-ext-blackhole-config;
   }

   augment "/oc-netinst:network-instances/oc-netinst:network-instance/oc-netinst:protocols/oc-netinst:protocol/oc-netinst:static-routes/oc-netinst:static/oc-netinst:next-hops/oc-netinst:next-hop/oc-netinst:state" {
      description
          "Next hop tag value";
      uses local-routing-ext-tag-config;
   }


}
