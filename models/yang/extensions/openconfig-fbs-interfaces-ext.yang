submodule openconfig-fbs-interfaces-ext {
  belongs-to openconfig-fbs-ext {
    prefix oc-fbs-ext;
  }

  // import some basic types
  import openconfig-interfaces { prefix oc-if; }
  import openconfig-extensions { prefix oc-ext; }
  import openconfig-yang-types { prefix oc-yang; }

  include openconfig-fbs-types-ext;
  include openconfig-fbs-policies-ext;
  include openconfig-fbs-next-hop-group-ext;

  // meta
  organization "SONiC";

  contact
    "SONiC
    https://github.com/Azure/SONiC";

  description
    "This model defines the configuration and operational data
    for flow based services interfaces";

  oc-ext:openconfig-version "0.1.0";

  revision "2020-05-15" {
    description
      "Initial revision";

    reference "0.1.0";
  }

  // extension statements

  // feature statements

  // identity statements

  // typedef statements

  // grouping statements
  grouping fbs-ext-interface-qos-top {
    description
      "Grouping for QoS policy applied per interface";

    container qos {
      description
        "Container for QoS policy configuration and state per interface";

      container config {
        description
          "Configuration for QoS policy application on interface";

        uses fbs-ext-interface-qos-config;
      }

      container state {
        config false;

        description
          "Operation state data for QoS policy application on interface";

        uses fbs-ext-interface-qos-config;
      }

      uses fbs-ext-interface-qos-sections-state;
    }
  }

  grouping fbs-ext-interface-qos-config {
    description
      "Grouping for QoS policy configuration";

    leaf policy-name {
      type leafref {
        path "../../../../../../policies/policy/config/name";
      }

      must "../../../../../../policies/policy[policy-name=current()]/config/type = 'POLICY_QOS'";

      description
        "Name of the QoS policy applied on the interface";
    }
  }

  grouping fbs-ext-interface-qos-sections-state {
    description
      "Grouping for QoS Policy operation state";

    container sections {
      config false;

      description
        "Container for Operational state of QoS Policy sections";

      list section {
        key "class-name";

        description
          "Operational state for QoS policy sections";

        leaf class-name {
          type leafref {
            path "../state/class-name";
          }

          description
            "Reference to the Classifier name used as section key";
        }

        container state {
          config false;

          description
            "Operational state of a QoS policy section";

          uses fbs-ext-section-common-state;
          uses fbs-ext-qos-section-state;
          uses fbs-ext-qos-policer-params-config;
        }
      }
    }
  }

  grouping fbs-ext-section-common-state {
    description
      "Grouping for common operational state data for all policy
      sections";

    leaf class-name {
      type string;

      description
        "Name of the classifier used for policy section.";
    }

    leaf active {
      type boolean;

      description
        "Indicates that the section is active ie the configured
        actions will be taken if the traffic matches the criteria
        used in the classifier";
    }

    leaf matched-packets {
      type oc-yang:counter64;

      description
        "Count of the number of packets matching the current
        classifier entry. This counter is specific to policy
        application to interface.";
    }

    leaf matched-octets {
      type oc-yang:counter64;

      description
        "Count of the number of bytes matching the current
        classifier.  This counter is specific to policy
        application to interface.";
    }
  }

  grouping fbs-ext-qos-section-state {
    description
      "Grouping for QoS counters like policers";

    leaf conforming-pkts {
      type oc-yang:counter64;
      description
        "The number of packets that were considered conforming by
        the policer.";
    }

    leaf conforming-octets {
      type oc-yang:counter64;
      description
        "The number of octets in packets that were considered
        conforming by the policer.";
    }

    leaf exceeding-pkts {
      type oc-yang:counter64;
      description
        "The number of packets that were considered exceeding by
        the policer.";
    }

    leaf exceeding-octets {
      type oc-yang:counter64;
      description
        "The number of octets in packets that were considered
        exceeding by the policer.";
    }

    leaf violating-pkts {
      type oc-yang:counter64;
      description
        "The number of packets that were considered violating by
        the policer.";
    }

    leaf violating-octets {
      type oc-yang:counter64;
      description
        "The number of octets in packets that were considered
        violating by the policer.";
    }
  }

  grouping fbs-ext-interface-monitoring-top {
    description
      "Grouping for monitoring policy applied per interface";

    container monitoring {
      description
        "Container for monitoring policy configuration and state per interface";

      container config {
        description
          "Configuration for monitoring policy application on interface";

        uses fbs-ext-interface-monitoring-config;
      }

      container state {
        config false;

        description
          "Operation state data for monitoring policy application on interface";

        uses fbs-ext-interface-monitoring-config;
      }

      uses fbs-ext-interface-monitoring-sections-state;
    }
  }

  grouping fbs-ext-interface-monitoring-config {
    description
      "Grouping for monitoring policy configuration";

    leaf policy-name {
      type leafref {
        path "../../../../../../policies/policy/config/name";
      }

      must "../../../../../../policies/policy[policy-name=current()]/config/type = 'POLICY_MONITORING'";

      description
        "Name of the monitoring policy applied on the interface";
    }
  }

  grouping fbs-ext-interface-monitoring-sections-state {
    description
      "Grouping for monitoring Policy operation state";

    container sections {
      config false;

      description
        "Container for Operational state of monitoring Policy sections";

      list section {
        key "class-name";

        description
          "Operational state for monitoring policy sections";

        leaf class-name {
          type leafref {
            path "../state/class-name";
          }

          description
            "Reference to the Classifier name used as section key";
        }

        container state {
          config false;

          description
            "Operational state of a monitoring policy section";

          uses fbs-ext-section-common-state;
        }
      }
    }
  }

  grouping fbs-ext-interface-forwarding-top {
    description
      "Grouping for forwarding policy applied per interface";

    container forwarding {
      description
        "Container for forwarding policy configuration and state per interface";

      container config {
        description
          "Configuration for forwarding policy application on interface";

        uses fbs-ext-interface-forwarding-config;
      }

      container state {
        config false;

        description
          "Operation state data for forwarding policy application on interface";

        uses fbs-ext-interface-forwarding-config;
      }

      uses fbs-ext-interface-forwarding-sections-state;
    }
  }

  grouping fbs-ext-interface-forwarding-config {
    description
      "Grouping for forwarding policy configuration";

    leaf policy-name {
      type leafref {
        path "../../../../../../policies/policy/config/name";
      }

      must "../../../../../../policies/policy[policy-name=current()]/config/type = 'POLICY_FORWARDING'";

      description
        "Name of the forwarding policy applied on the interface";
    }
  }

  grouping fbs-ext-interface-forwarding-sections-state {
    description
      "Grouping for forwarding Policy operation state";

    container sections {
      config false;

      description
        "Container for Operational state of forwarding Policy sections";

      list section {
        key "class-name";

        description
          "Operational state for forwarding policy sections";

        leaf class-name {
          type leafref {
            path "../state/class-name";
          }

          description
            "Reference to the Classifier name used as section key";
        }

        container state {
          config false;

          description
            "Operational state of a forwarding policy section";

          uses fbs-ext-section-common-state;
	      uses fbs-ext-forwarding-section-common-state;
        }

        uses fbs-ext-forwarding-section-l2-state;
        uses fbs-ext-forwarding-section-l3-state;
      }
    }
  }

  grouping fbs-ext-forwarding-section-common-state {
    description
      "Grouping for common forwarding operational state";

    leaf discard {
      type boolean;

      description
        "Indicates that traffic is dropped as none of the
        configured next-hops or egress interfaces are reachable.";
    }
  }

  grouping fbs-ext-forwarding-section-l3-state {
    description
      "Grouping for layer 3 forwarding operational state";

    container next-hop {
      description
        "Container for selected next-hop operational state.";

      container state {
        config false;

        description
          "Container for operation state of the selected next-hop";

        uses fbs-ext-layer3-fwd-next-hop-config;
      }
    }

    container next-hop-group {
      description
        "Next-hop group selected for forwarding";

      container state {
        config false;

        description
          "Container for operational state of next-hop group";

        leaf group-name {
          type string;

          description
            "Next hop group name";
        }

        leaf group-type {
          type identityref {
            base NEXT_HOP_GROUP_TYPE;
          }

          description
            "Next hop group type";
        }

        leaf priority {
          type uint16;

          description
            "Priority of the next-hop group";
        }
      }

      // uses fbs-ext-next-hop-group-members-state;
    }
  }

  grouping fbs-ext-forwarding-section-l2-state {
    description
      "Grouping for layer 2 forwarding operational state";

    container egress-interface {
      description
        "Container for selected egress interface operational state.";

      container state {
        config false;

        description
          "Container for operation state of the selected egress interface";

        uses fbs-ext-egress-interface-config;
      }
    }
  }

  grouping fbs-ext-cpu-port-copp-top {
    description
      "Grouping for CoPP policy applied to CPU";

    container copp {
      description
        "Container for CoPP policy configuration and state per interface";

      container config {
        description
          "Configuration for CoPP policy application on CPU";

        uses fbs-ext-cpu-port-copp-config;
      }

      container state {
        config false;

        description
          "Operation state data for CoPP policy configuration and state per interface";

        uses fbs-ext-cpu-port-copp-config;
      }

      uses fbs-ext-cpu-port-copp-sections-state;
    }
  }

  grouping fbs-ext-cpu-port-copp-config {
    description
      "Grouping for CoPP policy configuration";

    leaf policy-name {
      type leafref {
        path "../../../../../policies/policy/config/name";
      }

      must "../../../../../policies/policy[policy-name=current()]/config/type = 'POLICY_COPP'";

      description
        "Name of the CoPP policy applied";
    }
  }

  grouping fbs-ext-cpu-port-copp-sections-state {
    description
      "Grouping for monitoring Policy operation state";

    container sections {
      config false;

      description
        "Container for Operational state of monitoring Policy sections";

      list section {
        key "class-name";

        description
          "Operational state for monitoring policy sections";

        leaf class-name {
          type leafref {
            path "../state/class-name";
          }

          description
            "Reference to the Classifier name used as section key";
        }

        container state {
          config false;

          description
            "Operational state of a monitoring policy section";

          uses fbs-ext-section-common-state;
          uses fbs-ext-qos-section-state;
          uses fbs-ext-qos-policer-params-config;
        }
      }
    }
  }

  grouping fbs-ext-interfaces-config {
    description
      "Configuration data for interface references";

    leaf id {
      type oc-if:interface-id;
      description
        "User-defined identifier for the interface -- a common
        convention could be '<if name>.<subif index>'";
    }
  }

  grouping fbs-ext-interfaces-state {
    description
      "Operational state data for interface references";
  }

  grouping fbs-ext-interface-ingress-policies-top {
    description
      "Grouping for policies applied at ingress direction";

    container ingress-policies {
        description
          "Ingress policies configuration and operational state 
          container";

      container config {
        description
          "Configuration container for all ingress policies";
      }

      container state {
        config false;

        description
          "Configuration container for all ingress policies";
      }

      uses fbs-ext-interface-qos-top;
      uses fbs-ext-interface-monitoring-top;
      uses fbs-ext-interface-forwarding-top;
    }
  }

  grouping fbs-ext-interface-egress-policies-top {
    description
      "Grouping for policies applied at egress direction";

    container egress-policies {
        description
          "Ingress policies configuration and operational state 
          container";

      container config {
        description
          "Configuration container for all egress policies";
      }

      container state {
        config false;

        description
          "Configuration container for all egress policies";
      }

      uses fbs-ext-interface-qos-top;
      uses fbs-ext-interface-monitoring-top;
    }
  }

  grouping fbs-ext-cpu-ingress-policies-top {
    description
      "Grouping for policies applied at ingress direction";

    container ingress-policies {
      description
        "Ingress policies configuration and operational state
        container";

      container config {
        description
          "Configuration container for all ingress policies";
      }

      container state {
        config false;

        description
          "Configuration container for all ingress policies";
      }

      uses fbs-ext-cpu-port-copp-top;
    }
  }

  grouping fbs-ext-interface-next-hop-groups-top {
    description
      "TODO";

    container next-hop-groups {
      config false;

      description
        "TODO";

      list next-hop-group {
        key "group-name";

        description
          "TODO";

        leaf group-name {
          type leafref {
            path ../state/name;
          }

          description
            "Name of the next-hop group";
        }

        container state {
          config false;

          description
            "TODO";

          leaf name {
            type string;

            description
              "Next hop group name";
          }

          leaf group-type {
            type identityref {
              base NEXT_HOP_GROUP_TYPE;
            }

            description
              "Next hop group type";
          }

          leaf active {
            type boolean;

            description
              "Indicates if the group is active ie forwardable";
          }
        }

        uses fbs-ext-next-hop-group-members-state;
      }
    }
  }

  grouping fbs-ext-interfaces-top {
    description
      "Top-level grouping for interface-specific policies
      data";

    container interfaces {
      description
        "Enclosing container for the list of interfaces on which
        the flow based services policies are set";

      list interface {
        key "id";
        description
          "List of interfaces on which flow based services
          policies are set";

        leaf id {
          type leafref {
            path "../config/id";
          }
          description
            "Reference to the interface id list key";
        }

        container config {
          description
            "Configuration for per-interface group data";

          uses fbs-ext-interfaces-config;
        }

        container state {
          config false;

          description
            "Operational state for flow based services polices
            per-interface data";

          uses fbs-ext-interfaces-config;
          uses fbs-ext-interfaces-state;
        }

        uses oc-if:interface-ref;
        uses fbs-ext-interface-ingress-policies-top;
        uses fbs-ext-interface-egress-policies-top;
        uses fbs-ext-interface-next-hop-groups-top;
      }
    }

    container cpu-port {
        description 
        "Container for CPU port related configuration and operational state";

        container config {
          description
            "Configuration for CPU port policies";
        }

        container state {
          config false;

          description
            "Operational state for CPU port policies";
        }

        uses fbs-ext-cpu-ingress-policies-top;
    }
  }

  // data definition statements

  // augment statements

  // rpc statements

  // notification statements

}
