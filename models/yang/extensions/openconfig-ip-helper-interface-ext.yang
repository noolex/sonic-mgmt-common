submodule openconfig-ip-helper-interface-ext {
  belongs-to openconfig-interfaces-ext {
    prefix oc-if-ext;
  }

  // import some basic types
  import openconfig-interfaces { prefix oc-intf; }
  import openconfig-extensions { prefix oc-ext; }
  import openconfig-if-ip {prefix oc-ip; }

  // meta
  organization "SONiC";

  contact
    "SONiC
    https://github.com/Azure/SONiC";

  description
    "This model defines the configuration and operational data
    for ip helper interface parameters";

  oc-ext:openconfig-version "0.1.0";

  revision "2020-06-01" {
    description
      "Initial revision";

    reference "0.1.0";
  }

  // extension statements

  // feature statements

  // identity statements

  // typedef statements

  // grouping statements

  grouping interfaces-ext-ip-helper-servers-config {

    description
      "Grouping for IP helper server configuration data on an interface";

    leaf vrf {
      type string;
      description
        "Vrf of the server";
    }

    leaf ip {
      type string;
      description
        "IP address of the server";
    }

  }

  grouping interfaces-ext-ip-helper-servers-top {

    description
      "Top level grouping for IP helper Servers info";

    container servers {
      description
        "Enclosure for list of server addresses";

      list server {

        key "vrf ip";
        max-elements 4;
        description
          "List of server addresses";
                
        leaf vrf {
          type leafref {
            path "../config/vrf";
          }
          description
            "Vrf of the server";
        }

        leaf ip {
          type leafref {
            path "../config/ip";
          }
          description
            "IP address of the server";
        }

        container config {
          description
            "IP helper interface configuration data";
          uses interfaces-ext-ip-helper-servers-config;
        }

        container state {
          config false;
          description
            "IP helper interface operational state data";
          uses interfaces-ext-ip-helper-servers-config;
        }
      }
    }
  }

  grouping interfaces-ext-ip-helper-counters {

    description
      "Grouping for IP helper counters data on an interface";

    leaf received-packets {
      type uint64;
      description
        "Number of packets received";    
    }

    leaf relayed-packets {
      type uint64;
      description
        "Number of packets relayed";
    }

    leaf dropped-packets {
      type uint64;
      description
        "Number of packets dropped";
    }

    leaf packets-with-invalid-ttl {
      type uint64;
      description
        "Number of packets with invalid ttl";
    }

    leaf broadcast-packets {
      type uint64;
      description
        "Number of packets broadcast";
    }

    leaf net-broadcast-packets {
      type uint64;
      description
        "Number of packets net broadcast";
    }

  }

  grouping interfaces-ext-ip-helper-top {

    description
      "Grouping for top level IP helper information";
        
    container ip-helper {
      
      description
        "Top level container for IP helper information on interface";

      uses interfaces-ext-ip-helper-servers-top;

      container state {
        config false;
        description
          "Operational state data for IP helper on interface";
                
        container counters {
          description
            "Enclosing container for IP helper counters on interface";
            
          uses interfaces-ext-ip-helper-counters;
        }
      }
    }
  }

  // data definition statements

  // augment statements

  augment "/oc-intf:interfaces/oc-intf:interface/oc-intf:subinterfaces/oc-intf:subinterface/oc-ip:ipv4" {
    description
      "Ip helper config and state data.";
    uses interfaces-ext-ip-helper-top {
      description
        "IP helper interface config/state";
    }
  }

  // rpc statements

  // notification statements

}
