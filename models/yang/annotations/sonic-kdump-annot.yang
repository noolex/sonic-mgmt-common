module sonic-kdump-annot {

    yang-version "1.1";
    namespace "http://github.com/Azure/sonic-kdump-annot";
    prefix "kdump-annot";

    import sonic-extensions { prefix sonic-ext; }
    import sonic-kdump { prefix kdump; }

    deviation /kdump:sonic-kdump/kdump:KDUMP/kdump:KDUMP_LIST {
        deviate add {
            sonic-ext:table-name "KDUMP";
            sonic-ext:key-transformer "kdump_config_key_xfmr";
        }
    }
}
