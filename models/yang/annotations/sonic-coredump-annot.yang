module sonic-coredump-annot {

    yang-version "1.1";
    namespace "http://github.com/Azure/sonic-coredump-annot";
    prefix "coredump-annot";

    import sonic-extensions { prefix sonic-ext; }
    import sonic-coredump { prefix coredump; }

    deviation /coredump:sonic-coredump/coredump:COREDUMP/coredump:COREDUMP_LIST {
        deviate add {
            sonic-ext:table-name "COREDUMP";
            sonic-ext:key-transformer "coredump_config_key_xfmr";
        }
    }
}
