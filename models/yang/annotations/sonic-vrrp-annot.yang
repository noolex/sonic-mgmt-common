module sonic-vrrp-annot {

    namespace "http://github.com/Azure/sonic-vrrp-annot";
    prefix svrrp-annot;
    yang-version 1.1;

    import sonic-extensions { prefix sonic-ext; }
    import sonic-vrrp { prefix svrrp; }

    deviation /svrrp:get-vrrp {
        deviate add {
	        sonic-ext:rpc-callback "rpc_show_vrrp";
        }
    }

    deviation /svrrp:get-vrrp6 {
        deviate add {
	        sonic-ext:rpc-callback "rpc_show_vrrp6";
        }
    }

    deviation /svrrp:sonic-vrrp/svrrp:VRRP6_TRACK/svrrp:VRRP6_TRACK_LIST/svrrp:baseifname {
        deviate add {
            sonic-ext:value-transformer "vrrp_alias_xfmr";
        }
    }
    
    deviation /svrrp:sonic-vrrp/svrrp:VRRP_TRACK/svrrp:VRRP_TRACK_LIST/svrrp:baseifname {
        deviate add {
            sonic-ext:value-transformer "vrrp_alias_xfmr";
        }
    }

    deviation /svrrp:sonic-vrrp/svrrp:VRRP/svrrp:VRRP_LIST/svrrp:ifname {
        deviate add {
            sonic-ext:value-transformer "vrrp_alias_xfmr";
        }
    }

    deviation /svrrp:sonic-vrrp/svrrp:VRRP6/svrrp:VRRP6_LIST/svrrp:ifname {
        deviate add {
            sonic-ext:value-transformer "vrrp_alias_xfmr";
        }
    }

}
