module sonic-counters-annot {

    yang-version "1.1";

    namespace "http://openconfig.net/yang/annotation/scnts-annot";
    prefix "scnts-annot";

    import sonic-extensions { prefix sonic-ext; }
    import sonic-counters { prefix scnts; }

    deviation /scnts:interface_counters {
        deviate add {
	    sonic-ext:rpc-callback "rpc_get_interface_counters";
        }
    }
    deviation /scnts:clear_relay_counters {
        deviate add {
            sonic-ext:rpc-callback "rpc_clear_relay_counters";
        }
    }
    deviation /scnts:clear_rif_counters {
        deviate add {
            sonic-ext:rpc-callback "rpc_clear_rif_counters";
        }
    }
    deviation /scnts:rif_counters {
        deviate add {
            sonic-ext:rpc-callback "rpc_get_rif_counters";
        }
    }
}
