module openconfig-copp-annot {

    yang-version "1";

    namespace "http://openconfig.net/yang/annotation/oc-copp-annot";
    prefix "oc-copp-annot";

    import openconfig-extensions { prefix oc-ext; }
    import openconfig-copp { prefix oc-copp; }
    import sonic-extensions { prefix sonic-ext; }

    deviation /oc-copp:copp-config/oc-copp:copp-group {
      deviate add {
		  sonic-ext:table-name "COPP_GROUP";
      }
    }

    deviation /oc-copp:copp-config/oc-copp:copp-group/oc-copp:mode {
      deviate add {
		  sonic-ext:field-transformer "copp_mode_xfmr";
      }
    }

    deviation /oc-copp:copp-config/oc-copp:copp-group/oc-copp:trap-priority {
      deviate add {
		  sonic-ext:field-name "trap_priority";
      }
    }

    deviation /oc-copp:copp-config/oc-copp:copp-group/oc-copp:yellow-action {
      deviate add {
		  sonic-ext:field-transformer "copp_yellow_action_xfmr";
      }
    }

    deviation /oc-copp:copp-config/oc-copp:copp-group/oc-copp:trap-action {
      deviate add {
		  sonic-ext:field-transformer "copp_trap_action_xfmr";
      }
    }

    deviation /oc-copp:copp-config/oc-copp:copp-group/oc-copp:red-action {
      deviate add {
		  sonic-ext:field-transformer "copp_red_action_xfmr";
      }
    }

    deviation /oc-copp:copp-config/oc-copp:copp-group/oc-copp:meter-type {
      deviate add {
		  sonic-ext:field-transformer "copp_meter_type_xfmr";
      }
    }

    deviation /oc-copp:copp-config/oc-copp:copp-group/oc-copp:green-action {
      deviate add {
		  sonic-ext:field-transformer "copp_green_action_xfmr";
      }
    }

    deviation /oc-copp:copp-config/oc-copp:copp-trap {
      deviate add {
		  sonic-ext:table-name "COPP_TRAP";
      }
    }

    deviation /oc-copp:copp-config/oc-copp:copp-trap/oc-copp:trap-ids {
      deviate add {
		  sonic-ext:field-transformer "copp_trap_ids_xfmr";
      }
    }

    deviation /oc-copp:copp-config/oc-copp:copp-trap/oc-copp:trap-group {
      deviate add {
		  sonic-ext:field-name "trap_group";
      }
    }

}
