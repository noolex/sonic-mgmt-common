module openconfig-interfaces-ext-annot {

    yang-version "1";

    namespace "http://openconfig.net/yang/annotation/openconfig-interfaces-ext-annot";
    prefix "oc-interfaces-ext-annot";

    import sonic-extensions { prefix sonic-ext; }
    import openconfig-interfaces-ext { prefix oc-intf-ext; }

    deviation /oc-intf-ext:clear-counters {
        deviate add {
            sonic-ext:rpc-callback "rpc_oc_clear_counters";
        }
    }
    deviation /oc-intf-ext:vlan-replace {
        deviate add {
            sonic-ext:rpc-callback "rpc_oc_vlan_replace";
        }
    }
}
