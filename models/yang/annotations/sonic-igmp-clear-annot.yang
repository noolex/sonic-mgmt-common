module sonic-igmp-clear-annot {

    yang-version "1.1";

    namespace "http://openconfig.net/yang/annotation/sigmpclear-annot";
    prefix "sigmpclear-annot";

    import sonic-igmp { prefix sigmp; }
    import sonic-extensions { prefix sonic-ext; }

    deviation /sigmp:clear-igmp {
        deviate add {
            sonic-ext:rpc-callback "rpc_clear_igmp";
        }
    }
}
