module openconfig-spanning-tree-annot {

    yang-version "1.1";

    namespace "http://openconfig.net/yang/spanning-tree-annot";
    prefix "oc-stp-annot";

    import sonic-extensions { prefix sonic-ext; }
    import openconfig-spanning-tree { prefix oc-stp; }
    import openconfig-spanning-tree-ext { prefix oc-stp-ext; }

    // meta
    organization
       "SONiC";

    contact
       "SONiC";

    description
       "SONIC STP";

    revision 2020-04-16 {
       description
          "Initial revision.";
    }

    deviation /oc-stp:stp {
        deviate add {
            sonic-ext:pre-transformer "stp_pre_xfmr";
            sonic-ext:post-transformer "stp_post_xfmr";
        }
    }

	deviation /oc-stp:stp/oc-stp:global {
		deviate add {
			sonic-ext:subtree-transformer "stp_global_xfmr";
		}
    }

	deviation /oc-stp:stp/oc-stp:rapid-pvst/oc-stp:vlan {
		deviate add {
			sonic-ext:subtree-transformer "stp_vlan_xfmr";
		}
	}

	deviation /oc-stp:stp/oc-stp:rapid-pvst/oc-stp:vlan/oc-stp:interfaces/oc-stp:interface {
		deviate add {
			sonic-ext:subtree-transformer "stp_vlan_port_xfmr";
		}
	}

	deviation /oc-stp:stp/oc-stp:interfaces/oc-stp:interface { 
		deviate add {
            sonic-ext:table-name "STP_PORT";
		}
	}

	deviation /oc-stp:stp/oc-stp:interfaces/oc-stp:interface/oc-stp:config { 
		deviate add {
			sonic-ext:subtree-transformer "stp_port_xfmr";
		}
	}

	deviation /oc-stp:stp/oc-stp:interfaces/oc-stp:interface/oc-stp:state { 
		deviate add {
			sonic-ext:subtree-transformer "stp_port_xfmr";
		}
	}

	deviation /oc-stp:stp/oc-stp-ext:pvst/oc-stp-ext:vlan {
		deviate add {
			sonic-ext:subtree-transformer "stp_vlan_xfmr";
		}
	}

	deviation /oc-stp:stp/oc-stp-ext:pvst/oc-stp-ext:vlan/oc-stp-ext:interfaces/oc-stp-ext:interface {
		deviate add {
			sonic-ext:subtree-transformer "stp_vlan_port_xfmr";
		}
	}
}
