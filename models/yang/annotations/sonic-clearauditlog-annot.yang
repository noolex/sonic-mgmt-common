module sonic-clearauditlog-annot {

    yang-version "1";

    namespace "http://openconfig.net/Azure/sonic-clearauditlog-annot";
    prefix "clearauditlog-annot";

    import sonic-extensions { prefix sonic-ext; }
    import sonic-auditlog { prefix sal; }

    deviation /sal:clear-auditlog {
      deviate add {
        sonic-ext:rpc-callback "rpc_clearauditlog_cb";
      }
    }

}
