module openconfig-system-ext-annot {
    yang-version "1";
    namespace "http://openconfig.net/yang/openconfig-system-ext-annot";
    prefix "oc-sys-ext-annot";

    import sonic-extensions { prefix sonic-ext; }
    import openconfig-system-ext { prefix oc-sys-ext; }

    deviation /oc-sys-ext:tpcm-install{
        deviate add {
            sonic-ext:rpc-callback "rpc_tpcm_install_cb";
        }
    }

    deviation /oc-sys-ext:tpcm-uninstall{
        deviate add {
            sonic-ext:rpc-callback "rpc_tpcm_uninstall_cb";
        }
    }

    deviation /oc-sys-ext:tpcm-upgrade{
        deviate add {
            sonic-ext:rpc-callback "rpc_tpcm_upgrade_cb";
        }
    }

    deviation /oc-sys-ext:show-sys-log{
        deviate add {
            sonic-ext:rpc-callback "rpc_infra_show_sys_log_cb";
        }
    }

    deviation /oc-sys-ext:clear-sys-log{
        deviate add {
            sonic-ext:rpc-callback "rpc_infra_clear_sys_log_cb";
        }
    }
    deviation /oc-sys-ext:reboot-ops{
        deviate add {
            sonic-ext:rpc-callback "rpc_infra_reboot_cb";
        }
    }

    deviation /oc-sys-ext:sys-log-count{
        deviate add {
            sonic-ext:rpc-callback "rpc_infra_sys_log_count_cb";
        }
    }

    deviation /oc-sys-ext:set-loglevel-severity{
        deviate add {
            sonic-ext:rpc-callback "rpc_infra_set_loglevel_severity_cb";
        }
    }
    deviation /oc-sys-ext:get-loglevel-severity{
        deviate add {
            sonic-ext:rpc-callback "rpc_infra_get_loglevel_severity_cb";
        }
    }
    deviation /oc-sys-ext:show-sys-in-memory-log{
        deviate add {
            sonic-ext:rpc-callback "rpc_infra_show_sys_in_memory_log_cb";
        }
    }
    deviation /oc-sys-ext:sys-in-memory-log-count{
        deviate add {
            sonic-ext:rpc-callback "rpc_infra_sys_in_memory_log_count_cb";
        }
    }
    deviation /oc-sys-ext:locator-led-chassis-on{
        deviate add {
            sonic-ext:rpc-callback "rpc_locator_led_chassis_on_cb";
        }
    }
    deviation /oc-sys-ext:locator-led-chassis-off{
        deviate add {
            sonic-ext:rpc-callback "rpc_locator_led_chassis_off_cb";
        }
    }
    deviation /oc-sys-ext:show-locator-led-chassis{
        deviate add {
            sonic-ext:rpc-callback "rpc_show_locator_led_chassis_cb";
        }
    }
    deviation /oc-sys-ext:logger{
        deviate add {
            sonic-ext:rpc-callback "rpc_infra_logger_cb";
        }
    }
}
