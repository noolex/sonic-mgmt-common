module sonic-mgmt-interface-annot {

    yang-version "1.1";

    namespace "http://openconfig.net/yang/annotation/smgmtintf-annot";
    prefix "smgmtintf-annot";

    import sonic-extensions { prefix sonic-ext; }
    import sonic-interface { prefix sintf; }
    import sonic-mgmt-interface { prefix smgmt; }

    deviation /smgmt:sonic-mgmt-interface/smgmt:MGMT_INTF_TABLE {
        deviate add {
            sonic-ext:db-name "APPL_DB";
        }
    }
    deviation /smgmt:renew_dhcp_lease {
        deviate add {
            sonic-ext:rpc-callback "rpc_renew_dhcp_lease";
        }
    }

}
