module sonic-extensions {

  yang-version "1";

  // namespace
  namespace "http://openconfig.net/yang/sonic-ext";

  prefix "sonic-ext";

  // meta
  organization "Sonic working group";

  contact
    "OpenConfig working group
    www.openconfig.net";

  description
    "This module provides extensions to the YANG language to allow
    Sonic specific functionality and meta-data to be defined.";

  revision "2020-07-13" {
	  description
		  "Added extension for pre transformer support.";
  }
  revision "2020-05-06" {
    description
      "Add extensions for subscription support.";
  }

  revision "2019-08-30" {
    description
      "Add extensions for redis DB mappings to identify the Redis DB name.";
  }

  revision "2019-07-26" {
    description
      "Add extensionis for redis DB mappings for table, table-keys, table-fields and corresponding transformer methods.";
  }

  revision "2020-05-06" {
    description
      "Add extension for redis DB mappings for field values in redis table and corresponding transformer method.";
  }

  // extension statements
  extension table-name {
    argument "table-name";
    description "Db table name.";
  }

  extension key-transformer {
    argument "key-transformer-name";
    description "Db table key transformer name indicating that the list keys together form db table keys.";
  }

  extension key-delimiter {
    argument "key-delimiter-string";
    description "Db table key values delimiter.";
  }

  extension field-name {
    argument "field-name";
    description "Db table field name.";
  }

  extension field-transformer {
    argument "field-transformer-name";
    description "Db table field transformer name.This can be applied to either transform yang value to some different format
                 or choose a specific DB field based on the type of yang value.";
  }
  
  extension subtree-transformer {
    argument "subtree-transformer-name";
    description "Subtree/node level transformer name that will have db mappings for an entire yang subtree.";
  }

  extension post-transformer {
    argument "post-transformer-name";
    description "Transformer name that will perform post-translation tasks.";
  }

  extension get-validate {
	    argument "get-validate-name";
	    description "Validation callpoint used to validate a YANG node during data translation back to YANG as a response to GET.";
  }

  extension db-name {
    argument "db-name";
    description "DB name that will indicate where data is stored. Eg: Config DB, App DB etc";
  }

  extension key-delim {
    argument "key-delim";
    description "Key delimiter in DB";
  }

  extension table-transformer {
    argument "table-transformer-name";
    description "Db table transformer name.This can be applied to either transform yang value to some different format
                 or choose a specific DB table based on the type.";
  }

  extension cascade-delete {
    argument "cascade-delete";
    description "Cascade delete extension";
  }

  extension rpc-callback {
    argument "callback";
    description "RPC callback to be invoked for action";
  }

  extension subscribe-preference {
    argument "subscribe-preference";
    description "Subscription preference sample/onchange";
  }

  extension subscribe-on-change {
    argument "subscribe-on-change";
    description "Onchange subscription is enable/disable";
  }

  extension subscribe-min-interval {
    argument "subscribe-min-interval";
    description "Subscription sampling interval";
  }

  extension value-transformer {
    argument "value-transformer-name";
    description "Db table field/key value transformer name. This can be applied to transform yang value to some different format.";
  }

  extension table-owner {
    argument "table-owner-flag";
    description "Owner of the redis-db table.";
  }

  extension virtual-table {
    argument "virtual-table-flag";
    description "Table not present in redis-db.";
  }

  extension pre-transformer {
	  argument "pre-transformer-name";
	  description "Transformer name that will perform pre-translation tasks.";
  }

  extension path-transformer {
	  argument "path-transformer-name";
	  description "To mention the name of the path transformer which is to resolve the yang uri by filling the
	                yang keys in the path using the db table key information";
  }

  extension db-key-count {
      argument "db-key-count";
      description "To mention the database key component count for the table name annotated in the path";
  }

  extension composite-field-names {
  	  argument "composite-db-table-field-names";
  	  description "To mention one or more mapped db field and its table name entry for the same oc yang leaf/leaf-list node;
  	    Each entry should be separated by character comma(,). The format of the each entry should be in the form table-name:field-name.
  	    For example, the argument for this composite-db-field-names annotation is 'VLAN:mtu, PORT:mtu' ";
  }
}
