module openconfig-platform-annot {

    yang-version "1";
    namespace "http://openconfig.net/yang/platform-annot";
    prefix "oc-platform-annot";

    import openconfig-platform { prefix oc-platform; }
    import openconfig-platform-port { prefix oc-port; }
    import openconfig-port-breakout-ext { prefix oc-brk-ext; }
    import sonic-extensions { prefix sonic-ext; }
    import openconfig-platform-transceiver { prefix oc-transceiver; }
    import openconfig-platform-transceiver-ext { prefix oc-transceiver-ext; }
    import openconfig-port-media-fec-ext { prefix oc-port-media-fec; }

    deviation /oc-platform:components/oc-platform:component {
      deviate add {
        sonic-ext:subtree-transformer "pfm_components_xfmr";
      }
    }

    deviation /oc-platform:components/oc-platform:component/oc-platform:power-supply {
      deviate add {
        sonic-ext:subtree-transformer "pfm_components_psu_xfmr";
      }
    }

    deviation /oc-platform:components/oc-platform:component/oc-platform:fan {
      deviate add {
        sonic-ext:subtree-transformer "pfm_components_fan_xfmr";
      }
    }

    deviation /oc-platform:components/oc-platform:component/oc-platform:port/oc-platform:config/oc-port-media-fec:media-fec-mode{
      deviate add {
        sonic-ext:table-name "PORT";
        sonic-ext:field-transformer "media_fec_mode_xfmr";
        sonic-ext:key-transformer "media_fec_mode_key_xfmr";
      }
    }

    deviation /oc-platform:components/oc-platform:component/oc-platform:port/oc-platform:state/oc-port-media-fec:media-fec-mode{
      deviate add {
        sonic-ext:db-name "APPL_DB";
        sonic-ext:table-name "PORT_TABLE";
        sonic-ext:field-transformer "media_fec_mode_state_xfmr";
        sonic-ext:key-transformer "media_fec_mode_key_xfmr";
      }
    }


    deviation /oc-platform:components/oc-platform:component/oc-platform:port/oc-port:breakout-mode/oc-port:config {
      deviate add {
        sonic-ext:table-name "BREAKOUT_CFG";
        sonic-ext:subtree-transformer "port_breakout_config_xfmr";
      }
    }

    deviation /oc-platform:components/oc-platform:component/oc-platform:port/oc-port:breakout-mode/oc-port:state {
      deviate add {
        sonic-ext:db-name "STATE_DB";
        sonic-ext:subtree-transformer "port_breakout_state_xfmr";
      }
    }

    deviation /oc-platform:components/oc-platform:component/oc-platform:port/oc-port:breakout-mode/oc-port:state/oc-brk-ext:status {
      deviate add {
        sonic-ext:db-name "STATE_DB";
      }
    }

    deviation /oc-platform:components/oc-platform:component/oc-platform:port/oc-port:breakout-mode/oc-port:state/oc-brk-ext:members {
      deviate add {
        sonic-ext:db-name "CONFIG_DB";
      }
    }
    deviation /oc-platform:components/oc-platform:component/oc-transceiver:transceiver {
      deviate add {
        sonic-ext:db-name "CONFIG_DB";
        sonic-ext:subtree-transformer "pfm_components_transceiver_xfmr";
      }
    }
    deviation /oc-platform:components/oc-platform:component/oc-transceiver:transceiver/oc-transceiver-ext:diagnostics {
      deviate add {
        sonic-ext:subtree-transformer "pfm_components_transceiver_diag_xfmr";
      }
    }

    deviation /oc-platform:components/oc-platform:component/oc-platform:chassis {
      deviate add {
        sonic-ext:subtree-transformer "pfm_components_chassis_xfmr";
      }
    }
}
