module ietf-snmp-annot {

    yang-version "1";

    namespace "http://openconfig.net/yang/annotation/snmp-annot";
    prefix "snmp-annot";

    import ietf-snmp { prefix snmp; }
    import ietf-snmp-ext { prefix snmp-ext; }
    import sonic-extensions { prefix sonic-ext; }

    deviation /snmp:snmp {
      deviate add {
      }
    }

    deviation /snmp:snmp/snmp-ext:system {
      deviate add {
        sonic-ext:table-name "SNMP_SERVER";
        sonic-ext:db-name "CONFIG_DB";
        sonic-ext:key-transformer "snmp_system_key_xfmr";
      }
    }

    deviation /snmp:snmp/snmp-ext:system/snmp-ext:contact {
      deviate add {
        sonic-ext:field-name "sysContact";
      }
    }

    deviation /snmp:snmp/snmp-ext:system/snmp-ext:location {
      deviate add {
        sonic-ext:field-name "sysLocation";
      }
    }

    deviation /snmp:snmp/snmp-ext:system/snmp-ext:trap-enable {
      deviate add {
        sonic-ext:field-name "traps";
        sonic-ext:field-transformer "snmp_trap_fld_xfmr";
      }
    }

    deviation /snmp:snmp/snmp:community {
      deviate add {
        sonic-ext:table-name "SNMP_SERVER_COMMUNITY";
      }
    }

    deviation /snmp:snmp/snmp:community/snmp:index {
      deviate add {
        sonic-ext:field-name "index";
      }
    }

    deviation /snmp:snmp/snmp:community/snmp:security-name {
      deviate add {
        sonic-ext:field-name "securityName";
      }
    }

    deviation /snmp:snmp/snmp:engine {
      deviate add {
      }
    }

    deviation /snmp:snmp/snmp:engine/snmp:engine-id {
      deviate add {
        sonic-ext:table-name "SNMP_SERVER_ENGINE";
        sonic-ext:key-transformer "snmp_engine_key_xfmr";
        sonic-ext:field-name "engine-id";
      }
    }

    deviation /snmp:snmp/snmp:engine/snmp:version {
      deviate add {
      }
    }

    deviation /snmp:snmp/snmp:engine/snmp:version/snmp:v2c {
      deviate add {
      }
    }

    deviation /snmp:snmp/snmp:engine/snmp:version/snmp:v3 {
      deviate add {
      }
    }

    deviation /snmp:snmp/snmp:engine/snmp:listen {
      deviate add {
        sonic-ext:table-name "SNMP_AGENT_ADDRESS_CONFIG";
        sonic-ext:subtree-transformer "snmp_listen_subtree_xfmr";
        sonic-ext:path-transformer "snmp_listen_path_xfmr";
      }
    }

    deviation /snmp:snmp/snmp:engine/snmp:listen/snmp:name {
      deviate add {
      }
    }

    deviation /snmp:snmp/snmp:engine/snmp:listen/snmp:transport {
      deviate add {
      }
    }

    deviation /snmp:snmp/snmp:engine/snmp:listen/snmp:transport/snmp:udp {
      deviate add {
      }
    }

    deviation /snmp:snmp/snmp:engine/snmp:listen/snmp:transport/snmp:udp/snmp:udp {
      deviate add {
      }
    }

    deviation /snmp:snmp/snmp:engine/snmp:listen/snmp:transport/snmp:udp/snmp:udp/snmp:ip {
      deviate add {
        sonic-ext:field-name "ip";
      }
    }

    deviation /snmp:snmp/snmp:engine/snmp:listen/snmp:transport/snmp:udp/snmp:udp/snmp:port {
      deviate add {
        sonic-ext:field-name "port";
      }
    }

    deviation /snmp:snmp/snmp:engine/snmp:listen/snmp:transport/snmp:udp/snmp:udp/snmp-ext:interface {
      deviate add {
        sonic-ext:field-name "interface";
      }
    }

    deviation /snmp:snmp/snmp:notify {
      deviate add {
      }
    }

    deviation /snmp:snmp/snmp:notify/snmp:name {
      deviate add {
      }
    }

    deviation /snmp:snmp/snmp:notify/snmp:tag {
      deviate add {
      }
    }

    deviation /snmp:snmp/snmp:notify/snmp:type {
      deviate add {
      }
    }

    deviation /snmp:snmp/snmp:target {
      deviate add {
        sonic-ext:table-name "SNMP_SERVER_TARGET";
      }
    }

    deviation /snmp:snmp/snmp:target/snmp:name {
      deviate add {
        sonic-ext:field-name "name";
      }
    }

    deviation /snmp:snmp/snmp:target/snmp:tag {
      deviate add {
        sonic-ext:field-name "tag";
        sonic-ext:field-transformer "snmp_tag_name_xfmr";
      }
    }

    deviation /snmp:snmp/snmp:target/snmp:timeout {
      deviate add {
        sonic-ext:field-name "timeout";
      }
    }

    deviation /snmp:snmp/snmp:target/snmp:retries {
      deviate add {
        sonic-ext:field-name "retries";
      }
    }

    deviation /snmp:snmp/snmp:target/snmp:target-params {
      deviate add {
        sonic-ext:field-name "targetParams";
      }
    }

    deviation /snmp:snmp/snmp:target/snmp:transport {
      deviate add {
      }
    }

    deviation /snmp:snmp/snmp:target/snmp:transport/snmp:udp {
      deviate add {
      }
    }

    deviation /snmp:snmp/snmp:target/snmp:transport/snmp:udp/snmp:udp {
      deviate add {
      }
    }

    deviation /snmp:snmp/snmp:target/snmp:transport/snmp:udp/snmp:udp/snmp-ext:source-interface {
      deviate add {
        sonic-ext:field-name "source-interface";
      }
    }

    deviation /snmp:snmp/snmp:target/snmp:transport/snmp:udp/snmp:udp/snmp:ip {
      deviate add {
        sonic-ext:field-name "ip";
      }
    }

    deviation /snmp:snmp/snmp:target/snmp:transport/snmp:udp/snmp:udp/snmp:port {
      deviate add {
        sonic-ext:field-name "port";
      }
    }

    deviation /snmp:snmp/snmp:target-params {
      deviate add {
        sonic-ext:table-name "SNMP_SERVER_PARAMS";
      }
    }

    deviation /snmp:snmp/snmp:target-params/snmp:name {
      deviate add {
        sonic-ext:field-name "name";
      }
    }

    deviation /snmp:snmp/snmp:target-params/snmp:params {
      deviate add {
      }
    }

    deviation /snmp:snmp/snmp:target-params/snmp:params/snmp:v2c {
      deviate add {
      }
    }

    deviation /snmp:snmp/snmp:target-params/snmp:params/snmp:v2c/snmp:v2c {
      deviate add {
      }
    }

    deviation /snmp:snmp/snmp:target-params/snmp:params/snmp:v2c/snmp:v2c/snmp:security-name {
      deviate add {
        sonic-ext:field-name "securityNameV2";
      }
    }

    deviation /snmp:snmp/snmp:target-params/snmp:params/snmp:usm {
      deviate add {
      }
    }

    deviation /snmp:snmp/snmp:target-params/snmp:params/snmp:usm/snmp:usm {
      deviate add {
      }
    }

    deviation /snmp:snmp/snmp:target-params/snmp:params/snmp:usm/snmp:usm/snmp:user-name {
      deviate add {
        sonic-ext:field-name "user";
      }
    }

    deviation /snmp:snmp/snmp:target-params/snmp:params/snmp:usm/snmp:usm/snmp:security-level {
      deviate add {
        sonic-ext:field-name "security-level";
      }
    }
 
    deviation /snmp:snmp/snmp:usm {
      deviate add {
      }
    }

    deviation /snmp:snmp/snmp:usm/snmp:local {
      deviate add {
      }
    }

    deviation /snmp:snmp/snmp:usm/snmp:local/snmp:user {
      deviate add {
        sonic-ext:table-name "SNMP_SERVER_USER";
      }
    }

    deviation /snmp:snmp/snmp:usm/snmp:local/snmp:user/snmp:name {
      deviate add {
        sonic-ext:field-name "name";
      }
    }

    deviation /snmp:snmp/snmp:usm/snmp:local/snmp:user/snmp:auth {
      deviate add {
      }
    }

    deviation /snmp:snmp/snmp:usm/snmp:local/snmp:user/snmp:auth/snmp:protocol {
      deviate add {
      }
    }

    deviation /snmp:snmp/snmp:usm/snmp:local/snmp:user/snmp:auth/snmp:protocol/snmp:sha {
      deviate add {
      }
    }

    deviation /snmp:snmp/snmp:usm/snmp:local/snmp:user/snmp:auth/snmp:protocol/snmp:sha/snmp:sha {
      deviate add {
      }
    }

    deviation /snmp:snmp/snmp:usm/snmp:local/snmp:user/snmp:auth/snmp:protocol/snmp:sha/snmp:sha/snmp:key {
      deviate add {
        sonic-ext:field-name "shaKey";
      }
    }

    deviation /snmp:snmp/snmp:usm/snmp:local/snmp:user/snmp:auth/snmp:protocol/snmp:md5 {
      deviate add {
      }
    }

    deviation /snmp:snmp/snmp:usm/snmp:local/snmp:user/snmp:auth/snmp:protocol/snmp:md5/snmp:md5 {
      deviate add {
      }
    }

    deviation /snmp:snmp/snmp:usm/snmp:local/snmp:user/snmp:auth/snmp:protocol/snmp:md5/snmp:md5/snmp:key {
      deviate add {
        sonic-ext:field-name "md5Key";
      }
    }

    deviation /snmp:snmp/snmp:usm/snmp:local/snmp:user/snmp:priv {
      deviate add {
      }
    }

    deviation /snmp:snmp/snmp:usm/snmp:local/snmp:user/snmp:priv/snmp:protocol {
      deviate add {
      }
    }

    deviation /snmp:snmp/snmp:usm/snmp:local/snmp:user/snmp:priv/snmp:protocol/snmp:aes {
      deviate add {
      }
    }

    deviation /snmp:snmp/snmp:usm/snmp:local/snmp:user/snmp:priv/snmp:protocol/snmp:aes/snmp:aes {
      deviate add {
      }
    }

    deviation /snmp:snmp/snmp:usm/snmp:local/snmp:user/snmp:priv/snmp:protocol/snmp:aes/snmp:aes/snmp:key {
      deviate add {
        sonic-ext:field-name "aesKey";
      }
    }

    deviation /snmp:snmp/snmp:usm/snmp:local/snmp:user/snmp:priv/snmp:protocol/snmp:des {
      deviate add {
      }
    }

    deviation /snmp:snmp/snmp:usm/snmp:local/snmp:user/snmp:priv/snmp:protocol/snmp:des/snmp:des {
      deviate add {
      }
    }

    deviation /snmp:snmp/snmp:usm/snmp:local/snmp:user/snmp:priv/snmp:protocol/snmp:des/snmp:des/snmp:key {
      deviate add {
        sonic-ext:field-name "desKey";
      }
    }

    deviation /snmp:snmp/snmp:vacm {
      deviate add {
      }
    }

    deviation /snmp:snmp/snmp:vacm/snmp:group {
      deviate add {
        sonic-ext:table-name "SNMP_SERVER_GROUP";
      }
    }

    deviation /snmp:snmp/snmp:vacm/snmp:group/snmp:name {
      deviate add {
        sonic-ext:field-name "name";
        sonic-ext:field-transformer "snmp_group_name_xfmr";
      }
    }

    deviation /snmp:snmp/snmp:vacm/snmp:group/snmp:member {
      deviate add {
        sonic-ext:table-name "SNMP_SERVER_GROUP_MEMBER";
        sonic-ext:key-transformer "snmp_member_key_xfmr";
      }
    }

    deviation /snmp:snmp/snmp:vacm/snmp:group/snmp:member/snmp:security-name {
      deviate add {
        sonic-ext:field-name "securityName";
      }
    }

    deviation /snmp:snmp/snmp:vacm/snmp:group/snmp:member/snmp:security-model {
      deviate add {
        sonic-ext:field-name "securityModel";
      }
    }

    deviation /snmp:snmp/snmp:vacm/snmp:group/snmp:access {
      deviate add {
        sonic-ext:table-name "SNMP_SERVER_GROUP_ACCESS";
        sonic-ext:key-transformer "snmp_access_key_xfmr";
      }
    }

    deviation /snmp:snmp/snmp:vacm/snmp:group/snmp:access/snmp:context {
      deviate add {
        sonic-ext:field-name "context";
      }
    }

    deviation /snmp:snmp/snmp:vacm/snmp:group/snmp:access/snmp:context-match {
      deviate add {
        sonic-ext:field-name "contextMatch";
      }
    }

    deviation /snmp:snmp/snmp:vacm/snmp:group/snmp:access/snmp:security-model {
      deviate add {
        sonic-ext:field-name "securityModel";
      }
    }

    deviation /snmp:snmp/snmp:vacm/snmp:group/snmp:access/snmp:security-level {
      deviate add {
        sonic-ext:field-name "securityLevel";
      }
    }

    deviation /snmp:snmp/snmp:vacm/snmp:group/snmp:access/snmp:read-view {
      deviate add {
        sonic-ext:field-name "readView";
      }
    }

    deviation /snmp:snmp/snmp:vacm/snmp:group/snmp:access/snmp:write-view {
      deviate add {
        sonic-ext:field-name "writeView";
      }
    }

    deviation /snmp:snmp/snmp:vacm/snmp:group/snmp:access/snmp:notify-view {
      deviate add {
        sonic-ext:field-name "notifyView";
      }
    }

    deviation /snmp:snmp/snmp:vacm/snmp:view {
      deviate add {
        sonic-ext:table-name "SNMP_SERVER_VIEW";
      }
    }

    deviation /snmp:snmp/snmp:vacm/snmp:view/snmp:name {
      deviate add {
        sonic-ext:field-name "name";
      }
    }

    deviation /snmp:snmp/snmp:vacm/snmp:view/snmp:include {
      deviate add {
        sonic-ext:field-name "include";
      }
    }

    deviation /snmp:snmp/snmp:vacm/snmp:view/snmp:exclude {
      deviate add {
        sonic-ext:field-name "exclude";
      }
    }

}
