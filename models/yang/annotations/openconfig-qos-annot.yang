module openconfig-qos-annot {

    yang-version "1.1";

    namespace "http://openconfig.net/yang/qos-annot";
    prefix "oc-qos-annot";

    import sonic-extensions { prefix sonic-ext; }
    import openconfig-qos { prefix oc-qos; }
    import openconfig-qos-ext {prefix oc-qos-ext; }
    import openconfig-qos-maps-ext {prefix oc-qos-maps-ext; }

    deviation /oc-qos:qos {
      deviate add {
          sonic-ext:post-transformer "qos_post_xfmr";
      }
    }

    deviation /oc-qos:qos/oc-qos:interfaces/oc-qos:interface {
      deviate add {
          sonic-ext:key-transformer "qos_intf_tbl_key_xfmr";
          sonic-ext:table-transformer "qos_intf_table_xfmr";
          sonic-ext:table-owner "false";
      }
    }
    deviation /oc-qos:qos/oc-qos:interfaces/oc-qos:interface/oc-qos:interface-id {
        deviate add {
            sonic-ext:field-transformer "qos_intf_intf_id_fld_xfmr";
        }
    }

    deviation /oc-qos:qos/oc-qos:interfaces/oc-qos:interface/oc-qos:config/oc-qos:interface-id {
        deviate add {
            sonic-ext:field-transformer "qos_intf_intf_id_fld_xfmr";
        }
    }

    deviation /oc-qos:qos/oc-qos:interfaces/oc-qos:interface/oc-qos:state/oc-qos:interface-id {
        deviate add {
            sonic-ext:field-transformer "qos_intf_intf_id_fld_xfmr";
        }
    }

    deviation /oc-qos:qos/oc-qos:interfaces/oc-qos:interface/oc-qos:interface-ref/oc-qos:config/oc-qos:interface {
        deviate add {
            sonic-ext:field-transformer "qos_intf_intfref_intf_fld_xfmr";
        }
    }

    deviation /oc-qos:qos/oc-qos:interfaces/oc-qos:interface/oc-qos:interface-ref/oc-qos:state/oc-qos:interface {
        deviate add {
            sonic-ext:field-transformer "qos_intf_intfref_intf_fld_xfmr";
        }
    }

    deviation /oc-qos:qos/oc-qos:interfaces/oc-qos:interface/oc-qos:output {
      deviate add {
        sonic-ext:table-name "NONE";
      }
    }

    deviation /oc-qos:qos/oc-qos:interfaces/oc-qos:interface/oc-qos:output/oc-qos:queues {
      deviate add {
        sonic-ext:subtree-transformer "qos_get_one_intf_all_q_counters_xfmr";
        sonic-ext:db-name "COUNTERS_DB";
        sonic-ext:virtual-table "true";
      }
    }

    deviation /oc-qos:qos/oc-qos:interfaces/oc-qos:interface/oc-qos:output/oc-qos:scheduler-policy {
      deviate add {
        sonic-ext:subtree-transformer "qos_intf_sched_policy_xfmr";
        sonic-ext:db-name "CONFIG_DB";
      }
    }

    deviation /oc-qos:qos/oc-qos:interfaces/oc-qos:interface/oc-qos:input {
      deviate add {
        sonic-ext:table-name "NONE";
      }
    }

    deviation /oc-qos:qos/oc-qos:interfaces/oc-qos:interface/oc-qos:input/oc-qos-ext:priority-groups {
      deviate add {
        sonic-ext:subtree-transformer "qos_get_one_intf_all_pg_counters_xfmr";
        sonic-ext:db-name "COUNTERS_DB";
        sonic-ext:virtual-table "true";
      }
    }

    deviation /oc-qos:qos/oc-qos:interfaces/oc-qos:interface/oc-qos-ext:pfc {
      deviate add {
        sonic-ext:table-name "NONE";
        sonic-ext:subtree-transformer "qos_intf_pfc_xfmr";
        sonic-ext:virtual-table "true";
      }
    }

	deviation /oc-qos:qos/oc-qos-ext:thresholds {
		deviate add {
            sonic-ext:table-name "NONE";
			sonic-ext:db-name "CONFIG_DB";
			sonic-ext:key-delim "|";
		}
	}

	deviation /oc-qos:qos/oc-qos-ext:thresholds/oc-qos-ext:threshold {
		deviate add {
			sonic-ext:table-name "THRESHOLD_TABLE";
			sonic-ext:key-transformer "tam_threshold_key_xfmr";
		}
	}

	deviation /oc-qos:qos/oc-qos-ext:thresholds/oc-qos-ext:threshold/oc-qos-ext:config {
		deviate add {
		}
	}

	deviation /oc-qos:qos/oc-qos-ext:thresholds/oc-qos-ext:threshold/oc-qos-ext:config/oc-qos-ext:buffer {
		deviate add {
			sonic-ext:field-transformer "tam_threshold_field_xfmr";

		}
	}

	deviation /oc-qos:qos/oc-qos-ext:thresholds/oc-qos-ext:threshold/oc-qos-ext:config/oc-qos-ext:type {
		deviate add {
			sonic-ext:field-transformer "tam_threshold_field_xfmr";

		}
	}

	deviation /oc-qos:qos/oc-qos-ext:thresholds/oc-qos-ext:threshold/oc-qos-ext:config/oc-qos-ext:port {
		deviate add {
			sonic-ext:field-transformer "tam_threshold_field_xfmr";

		}
	}

	deviation /oc-qos:qos/oc-qos-ext:thresholds/oc-qos-ext:threshold/oc-qos-ext:config/oc-qos-ext:index {
		deviate add {
			sonic-ext:field-transformer "tam_threshold_field_xfmr";

		}
	}

	deviation /oc-qos:qos/oc-qos-ext:thresholds/oc-qos-ext:threshold/oc-qos-ext:config/oc-qos-ext:threshold-value {
		deviate add {
			sonic-ext:field-name "threshold";
		}
	}

	deviation /oc-qos:qos/oc-qos-ext:thresholds/oc-qos-ext:threshold/oc-qos-ext:state/oc-qos-ext:buffer {
		deviate add {
		}
	}

	deviation /oc-qos:qos/oc-qos-ext:thresholds/oc-qos-ext:threshold/oc-qos-ext:state/oc-qos-ext:type {
		deviate add {

		}
	}

	deviation /oc-qos:qos/oc-qos-ext:thresholds/oc-qos-ext:threshold/oc-qos-ext:state/oc-qos-ext:port {
		deviate add {

		}
	}

	deviation /oc-qos:qos/oc-qos-ext:thresholds/oc-qos-ext:threshold/oc-qos-ext:state/oc-qos-ext:index {
		deviate add {

		}
	}

	deviation /oc-qos:qos/oc-qos-ext:thresholds/oc-qos-ext:threshold/oc-qos-ext:state/oc-qos-ext:threshold-value {
		deviate add {
			sonic-ext:field-name "threshold";
		}
	}

	deviation /oc-qos:qos/oc-qos-ext:thresholds/oc-qos-ext:threshold/oc-qos-ext:buffer {
		deviate add {
			sonic-ext:field-name "buffer";
		}
    }

    deviation /oc-qos:qos/oc-qos-ext:thresholds/oc-qos-ext:threshold/oc-qos-ext:type {
      deviate add {
          sonic-ext:field-name "threshold_buffer_type";
      }
    }

    deviation /oc-qos:qos/oc-qos-ext:thresholds/oc-qos-ext:threshold/oc-qos-ext:port {
      deviate add {
          sonic-ext:field-name "interface_name";
      }
    }

    deviation /oc-qos:qos/oc-qos-ext:thresholds/oc-qos-ext:threshold/oc-qos-ext:index {
      deviate add {
          sonic-ext:field-name "buffer_index_per_port";
      }
    }

	deviation /oc-qos:qos/oc-qos-ext:watermark {
		deviate add {
			sonic-ext:db-name "CONFIG_DB";
			sonic-ext:key-delim "|";
		}
	}

	deviation /oc-qos:qos/oc-qos-ext:watermark/oc-qos-ext:config {
		deviate add {
			sonic-ext:table-name "SNAPSHOT_TABLE";
			sonic-ext:key-transformer "tam_watermark_key_xfmr";
		}
	}

	deviation /oc-qos:qos/oc-qos-ext:watermark/oc-qos-ext:config/oc-qos-ext:refresh-interval {
		deviate add {
			sonic-ext:field-name "interval";
		}
	}

	deviation /oc-qos:qos/oc-qos-ext:watermark/oc-qos-ext:state {
		deviate add {
			sonic-ext:table-name "SNAPSHOT_TABLE";
			sonic-ext:key-transformer "tam_watermark_key_xfmr";
		}
	}

	deviation /oc-qos:qos/oc-qos-ext:watermark/oc-qos-ext:state/oc-qos-ext:refresh-interval {
		deviate add {
			sonic-ext:field-name "interval";
		}
	}


	deviation /oc-qos:qos/oc-qos-ext:telemetry-watermark {
		deviate add {
			sonic-ext:db-name "CONFIG_DB";
			sonic-ext:key-delim "|";
		}
	}

	deviation /oc-qos:qos/oc-qos-ext:telemetry-watermark/oc-qos-ext:config {
		deviate add {
			sonic-ext:table-name "WATERMARK_TABLE";
			sonic-ext:key-transformer "telemetry_watermark_key_xfmr";
		}
	}

	deviation /oc-qos:qos/oc-qos-ext:telemetry-watermark/oc-qos-ext:config/oc-qos-ext:refresh-interval {
		deviate add {
			sonic-ext:field-name "interval";
		}
	}

	deviation /oc-qos:qos/oc-qos-ext:telemetry-watermark/oc-qos-ext:state {
		deviate add {
			sonic-ext:table-name "WATERMARK_TABLE";
			sonic-ext:key-transformer "telemetry_watermark_key_xfmr";
		}
	}

	deviation /oc-qos:qos/oc-qos-ext:telemetry-watermark/oc-qos-ext:state/oc-qos-ext:refresh-interval {
		deviate add {
			sonic-ext:field-name "interval";
		}
	}

 
    deviation /oc-qos:qos/oc-qos-ext:threshold-breaches {
      deviate add {
        sonic-ext:db-name "COUNTERS_DB";
      }
    }

    deviation /oc-qos:qos/oc-qos-ext:threshold-breaches/oc-qos-ext:breach {
      deviate add {
        sonic-ext:table-name "THRESHOLD_BREACH_TABLE";
        sonic-ext:key-transformer "qos_threshold_breach_key_xfmr";
        sonic-ext:key-delim ":";
      }
    }

    deviation /oc-qos:qos/oc-qos-ext:threshold-breaches/oc-qos-ext:breach/oc-qos-ext:state/oc-qos-ext:breach-value {
      deviate add {
        sonic-ext:field-name "breach_value";
      }
    }

    deviation /oc-qos:qos/oc-qos-ext:threshold-breaches/oc-qos-ext:breach/oc-qos-ext:state/oc-qos-ext:counter {
      deviate add {
        sonic-ext:field-transformer "threshold_breach_counter_field_xfmr";
      }
    }

    deviation /oc-qos:qos/oc-qos-ext:threshold-breaches/oc-qos-ext:breach/oc-qos-ext:state/oc-qos-ext:buffer {
      deviate add {
        sonic-ext:field-name "buffer";
      }
    }

    deviation /oc-qos:qos/oc-qos-ext:threshold-breaches/oc-qos-ext:breach/oc-qos-ext:state/oc-qos-ext:type {
      deviate add {
        sonic-ext:field-name "type";
      }
    }

    deviation /oc-qos:qos/oc-qos-ext:threshold-breaches/oc-qos-ext:breach/oc-qos-ext:state/oc-qos-ext:port {
      deviate add {
        sonic-ext:field-name "port";
      }
    }

    deviation /oc-qos:qos/oc-qos-ext:threshold-breaches/oc-qos-ext:breach/oc-qos-ext:state/oc-qos-ext:index {
      deviate add {
        sonic-ext:field-name "index";
      }
    }

    deviation /oc-qos:qos/oc-qos-ext:threshold-breaches/oc-qos-ext:breach/oc-qos-ext:state/oc-qos-ext:time-stamp {
      deviate add {
        sonic-ext:field-name "time-stamp";
      }
    }

    deviation /oc-qos:qos/oc-qos:queues {
      deviate add {
        sonic-ext:table-name "NONE";
      }
    }

    deviation /oc-qos:qos/oc-qos:queues/oc-qos:queue {
      deviate add {
        sonic-ext:table-name "QUEUE";
        sonic-ext:key-transformer "qos_queue_key_xfmr";
        sonic-ext:key-delim "|";
      }
    }

    deviation /oc-qos:qos/oc-qos:queues/oc-qos:queue/oc-qos:config/oc-qos:name {
      deviate add {
        sonic-ext:field-transformer "qos_queue_fld_xfmr";
      }
    }

    deviation /oc-qos:qos/oc-qos:queues/oc-qos:queue/oc-qos:state/oc-qos:name {
      deviate add {
        sonic-ext:field-transformer "qos_queue_fld_xfmr";
      }
    }

    deviation /oc-qos:qos/oc-qos:queues/oc-qos:queue/oc-qos:wred/oc-qos:config/oc-qos-ext:wred-profile {
      deviate add {
        sonic-ext:field-transformer "qos_queue_wred_profile_fld_xfmr";
      }
    }


    deviation /oc-qos:qos/oc-qos:queues/oc-qos:queue/oc-qos:wred/oc-qos:state/oc-qos-ext:wred-profile {
      deviate add {
        sonic-ext:field-transformer "qos_queue_wred_profile_fld_xfmr";
      }
    }

    deviation /oc-qos:qos/oc-qos:scheduler-policies {
      deviate add {
        sonic-ext:table-name "NONE";
      }
    }

    deviation /oc-qos:qos/oc-qos:scheduler-policies/oc-qos:scheduler-policy {
      deviate add {
        sonic-ext:subtree-transformer "qos_scheduler_xfmr";
      }
    }

    deviation /oc-qos:qos/oc-qos-ext:wred-profiles {
      deviate add {
        sonic-ext:table-name "NONE";
      }
    }

    deviation /oc-qos:qos/oc-qos-ext:wred-profiles/oc-qos-ext:wred-profile {
      deviate add {
        sonic-ext:table-name "WRED_PROFILE";
      }
    }

    deviation /oc-qos:qos/oc-qos-ext:wred-profiles/oc-qos-ext:wred-profile/oc-qos-ext:name {
      deviate add {
        sonic-ext:field-transformer "wred_profile_name_empty_fld_xfmr";
      }
    }

    deviation /oc-qos:qos/oc-qos-ext:wred-profiles/oc-qos-ext:wred-profile/oc-qos-ext:config/oc-qos-ext:name {
      deviate add {
        sonic-ext:field-transformer "wred_profile_name_fld_xfmr";
      }
    }

    deviation /oc-qos:qos/oc-qos-ext:wred-profiles/oc-qos-ext:wred-profile/oc-qos-ext:state/oc-qos-ext:name {
      deviate add {
        sonic-ext:field-transformer "wred_profile_name_fld_xfmr";
      }
    }

    deviation /oc-qos:qos/oc-qos-ext:wred-profiles/oc-qos-ext:wred-profile/oc-qos-ext:config/oc-qos-ext:ecn {
      deviate add {
        sonic-ext:field-transformer "wred_ecn_fld_xfmr";
      }
    }

    deviation /oc-qos:qos/oc-qos-ext:wred-profiles/oc-qos-ext:wred-profile/oc-qos-ext:state/oc-qos-ext:ecn {
      deviate add {
        sonic-ext:field-transformer "wred_ecn_fld_xfmr";
      }
    }

    deviation /oc-qos:qos/oc-qos-ext:wred-profiles/oc-qos-ext:wred-profile/oc-qos-ext:config/oc-qos-ext:green-min-threshold {
      deviate add {
        sonic-ext:field-name "green_min_threshold";
      }
    }

    deviation /oc-qos:qos/oc-qos-ext:wred-profiles/oc-qos-ext:wred-profile/oc-qos-ext:config/oc-qos-ext:green-max-threshold {
      deviate add {
        sonic-ext:field-name "green_max_threshold";
      }
    }

    deviation /oc-qos:qos/oc-qos-ext:wred-profiles/oc-qos-ext:wred-profile/oc-qos-ext:config/oc-qos-ext:wred-green-enable {
      deviate add {
        sonic-ext:field-name "wred_green_enable";
      }
    }

    deviation /oc-qos:qos/oc-qos-ext:wred-profiles/oc-qos-ext:wred-profile/oc-qos-ext:config/oc-qos-ext:green-drop-probability {
      deviate add {
        sonic-ext:field-name "green_drop_probability";
      }
    }

    deviation /oc-qos:qos/oc-qos-ext:wred-profiles/oc-qos-ext:wred-profile/oc-qos-ext:state/oc-qos-ext:green-min-threshold {
      deviate add {
        sonic-ext:field-name "green_min_threshold";
      }
    }

    deviation /oc-qos:qos/oc-qos-ext:wred-profiles/oc-qos-ext:wred-profile/oc-qos-ext:state/oc-qos-ext:green-max-threshold {
      deviate add {
        sonic-ext:field-name "green_max_threshold";
      }
    }

    deviation /oc-qos:qos/oc-qos-ext:wred-profiles/oc-qos-ext:wred-profile/oc-qos-ext:state/oc-qos-ext:wred-green-enable {
      deviate add {
        sonic-ext:field-name "wred_green_enable";
      }
    }

    deviation /oc-qos:qos/oc-qos-ext:wred-profiles/oc-qos-ext:wred-profile/oc-qos-ext:state/oc-qos-ext:green-drop-probability {
      deviate add {
        sonic-ext:field-name "green_drop_probability";
      }
    }
  
   deviation /oc-qos:qos/oc-qos-ext:wred-profiles/oc-qos-ext:wred-profile/oc-qos-ext:config/oc-qos-ext:yellow-min-threshold {
      deviate add {
        sonic-ext:field-name "yellow_min_threshold";
      }
    }
 
    deviation /oc-qos:qos/oc-qos-ext:wred-profiles/oc-qos-ext:wred-profile/oc-qos-ext:config/oc-qos-ext:yellow-max-threshold {
      deviate add {
        sonic-ext:field-name "yellow_max_threshold";
      }
    }
 
    deviation /oc-qos:qos/oc-qos-ext:wred-profiles/oc-qos-ext:wred-profile/oc-qos-ext:config/oc-qos-ext:wred-yellow-enable {
      deviate add {
        sonic-ext:field-name "wred_yellow_enable";
      }
    }
 
    deviation /oc-qos:qos/oc-qos-ext:wred-profiles/oc-qos-ext:wred-profile/oc-qos-ext:config/oc-qos-ext:yellow-drop-probability {
      deviate add {
        sonic-ext:field-name "yellow_drop_probability";
      }
    }
  
    deviation /oc-qos:qos/oc-qos-ext:wred-profiles/oc-qos-ext:wred-profile/oc-qos-ext:state/oc-qos-ext:yellow-min-threshold {
      deviate add {
        sonic-ext:field-name "yellow_min_threshold";
      }
    }
 
    deviation /oc-qos:qos/oc-qos-ext:wred-profiles/oc-qos-ext:wred-profile/oc-qos-ext:state/oc-qos-ext:yellow-max-threshold {
      deviate add {
        sonic-ext:field-name "yellow_max_threshold";
      }
    }
 
    deviation /oc-qos:qos/oc-qos-ext:wred-profiles/oc-qos-ext:wred-profile/oc-qos-ext:state/oc-qos-ext:wred-yellow-enable {
      deviate add {
        sonic-ext:field-name "wred_yellow_enable";
      }
    }
 
    deviation /oc-qos:qos/oc-qos-ext:wred-profiles/oc-qos-ext:wred-profile/oc-qos-ext:state/oc-qos-ext:yellow-drop-probability {
      deviate add {
        sonic-ext:field-name "yellow_drop_probability";
      }
    }
   
   deviation /oc-qos:qos/oc-qos-ext:wred-profiles/oc-qos-ext:wred-profile/oc-qos-ext:config/oc-qos-ext:red-min-threshold {
      deviate add {
        sonic-ext:field-name "red_min_threshold";
      }
    }
 
    deviation /oc-qos:qos/oc-qos-ext:wred-profiles/oc-qos-ext:wred-profile/oc-qos-ext:config/oc-qos-ext:red-max-threshold {
      deviate add {
        sonic-ext:field-name "red_max_threshold";
      }
    }
 
    deviation /oc-qos:qos/oc-qos-ext:wred-profiles/oc-qos-ext:wred-profile/oc-qos-ext:config/oc-qos-ext:wred-red-enable {
      deviate add {
        sonic-ext:field-name "wred_red_enable";
      }
    }
 
    deviation /oc-qos:qos/oc-qos-ext:wred-profiles/oc-qos-ext:wred-profile/oc-qos-ext:config/oc-qos-ext:red-drop-probability {
      deviate add {
        sonic-ext:field-name "red_drop_probability";
      }
    }
  
    deviation /oc-qos:qos/oc-qos-ext:wred-profiles/oc-qos-ext:wred-profile/oc-qos-ext:state/oc-qos-ext:red-min-threshold {
      deviate add {
        sonic-ext:field-name "red_min_threshold";
      }
    }
 
    deviation /oc-qos:qos/oc-qos-ext:wred-profiles/oc-qos-ext:wred-profile/oc-qos-ext:state/oc-qos-ext:red-max-threshold {
      deviate add {
        sonic-ext:field-name "red_max_threshold";
      }
    }
 
    deviation /oc-qos:qos/oc-qos-ext:wred-profiles/oc-qos-ext:wred-profile/oc-qos-ext:state/oc-qos-ext:wred-red-enable {
      deviate add {
        sonic-ext:field-name "wred_red_enable";
      }
    }
 
    deviation /oc-qos:qos/oc-qos-ext:wred-profiles/oc-qos-ext:wred-profile/oc-qos-ext:state/oc-qos-ext:red-drop-probability {
      deviate add {
        sonic-ext:field-name "red_drop_probability";
      }
    }

    deviation /oc-qos:qos/oc-qos-maps-ext:dscp-maps {
        deviate add {
            sonic-ext:table-name "NONE";
        }
    }

    deviation /oc-qos:qos/oc-qos-maps-ext:dscp-maps/oc-qos-maps-ext:dscp-map {
        deviate add {
            sonic-ext:subtree-transformer "qos_dscp_fwd_group_xfmr";
        }
    }

    deviation /oc-qos:qos/oc-qos-maps-ext:dot1p-maps/oc-qos-maps-ext:dot1p-map {
        deviate add {
            sonic-ext:subtree-transformer "qos_dot1p_fwd_group_xfmr";
        }
    }

    deviation /oc-qos:qos/oc-qos-maps-ext:forwarding-group-queue-maps/oc-qos-maps-ext:forwarding-group-queue-map {
        deviate add {
            sonic-ext:subtree-transformer "qos_tc_queue_xfmr";
        }
    }

    deviation /oc-qos:qos/oc-qos-maps-ext:forwarding-group-priority-group-maps/oc-qos-maps-ext:forwarding-group-priority-group-map {
        deviate add {
            sonic-ext:subtree-transformer "qos_tc_pg_xfmr";
        }
    }

    deviation /oc-qos:qos/oc-qos-maps-ext:pfc-priority-queue-maps/oc-qos-maps-ext:pfc-priority-queue-map {
        deviate add {
            sonic-ext:subtree-transformer "qos_pfc_priority_queue_xfmr";
        }
    }

    deviation /oc-qos:qos/oc-qos-maps-ext:forwarding-group-dscp-maps/oc-qos-maps-ext:forwarding-group-dscp-map {
        deviate add {
            sonic-ext:subtree-transformer "qos_fwd_group_dscp_xfmr";
        }
    }

    deviation /oc-qos:qos/oc-qos-maps-ext:forwarding-group-dot1p-maps/oc-qos-maps-ext:forwarding-group-dot1p-map {
        deviate add {
            sonic-ext:subtree-transformer "qos_fwd_group_dot1p_xfmr";
        }
    }

    deviation /oc-qos:qos/oc-qos:interfaces/oc-qos:interface/oc-qos-maps-ext:interface-maps {
      deviate add {
		sonic-ext:table-name "PORT_QOS_MAP";
	  }
	}

    deviation /oc-qos:qos/oc-qos:interfaces/oc-qos:interface/oc-qos-maps-ext:interface-maps/oc-qos-maps-ext:config/oc-qos-maps-ext:dscp-to-forwarding-group {
      deviate add {
        sonic-ext:field-transformer "qos_dscp_to_tc_map_fld_xfmr";
      }
    }

    deviation /oc-qos:qos/oc-qos:interfaces/oc-qos:interface/oc-qos-maps-ext:interface-maps/oc-qos-maps-ext:config/oc-qos-maps-ext:dot1p-to-forwarding-group {
      deviate add {
        sonic-ext:field-transformer "qos_dot1p_to_tc_map_fld_xfmr";
      }
    }

    deviation /oc-qos:qos/oc-qos:interfaces/oc-qos:interface/oc-qos-maps-ext:interface-maps/oc-qos-maps-ext:config/oc-qos-maps-ext:forwarding-group-to-queue {
      deviate add {
        sonic-ext:field-transformer "qos_tc_to_queue_map_fld_xfmr";
      }
    }

    deviation /oc-qos:qos/oc-qos:interfaces/oc-qos:interface/oc-qos-maps-ext:interface-maps/oc-qos-maps-ext:config/oc-qos-maps-ext:forwarding-group-to-priority-group {
      deviate add {
        sonic-ext:field-transformer "qos_tc_to_pg_map_fld_xfmr";
      }
    }

    deviation /oc-qos:qos/oc-qos:interfaces/oc-qos:interface/oc-qos-maps-ext:interface-maps/oc-qos-maps-ext:config/oc-qos-maps-ext:pfc-priority-to-queue {
      deviate add {
        sonic-ext:field-transformer "qos_pfc_priority_to_queue_map_fld_xfmr";
      }
    }

    deviation /oc-qos:qos/oc-qos:interfaces/oc-qos:interface/oc-qos-maps-ext:interface-maps/oc-qos-maps-ext:config/oc-qos-maps-ext:forwarding-group-to-dscp {
      deviate add {
        sonic-ext:field-transformer "qos_tc_to_dscp_map_fld_xfmr";
      }
    }

    deviation /oc-qos:qos/oc-qos:interfaces/oc-qos:interface/oc-qos-maps-ext:interface-maps/oc-qos-maps-ext:config/oc-qos-maps-ext:forwarding-group-to-dot1p {
      deviate add {
        sonic-ext:field-transformer "qos_tc_to_dot1p_map_fld_xfmr";
      }
    }

    deviation /oc-qos:qos/oc-qos:interfaces/oc-qos:interface/oc-qos-maps-ext:interface-maps/oc-qos-maps-ext:state/oc-qos-maps-ext:dscp-to-forwarding-group {
      deviate add {
        sonic-ext:field-transformer "qos_dscp_to_tc_map_fld_xfmr";
      }
    }

    deviation /oc-qos:qos/oc-qos:interfaces/oc-qos:interface/oc-qos-maps-ext:interface-maps/oc-qos-maps-ext:state/oc-qos-maps-ext:dot1p-to-forwarding-group {
      deviate add {
        sonic-ext:field-transformer "qos_dot1p_to_tc_map_fld_xfmr";
      }
    }

    deviation /oc-qos:qos/oc-qos:interfaces/oc-qos:interface/oc-qos-maps-ext:interface-maps/oc-qos-maps-ext:state/oc-qos-maps-ext:forwarding-group-to-queue {
      deviate add {
        sonic-ext:field-transformer "qos_tc_to_queue_map_fld_xfmr";
      }
    }

    deviation /oc-qos:qos/oc-qos:interfaces/oc-qos:interface/oc-qos-maps-ext:interface-maps/oc-qos-maps-ext:state/oc-qos-maps-ext:forwarding-group-to-priority-group {
      deviate add {
        sonic-ext:field-transformer "qos_tc_to_pg_map_fld_xfmr";
      }
    }

    deviation /oc-qos:qos/oc-qos:interfaces/oc-qos:interface/oc-qos-maps-ext:interface-maps/oc-qos-maps-ext:state/oc-qos-maps-ext:pfc-priority-to-queue {
      deviate add {
        sonic-ext:field-transformer "qos_pfc_priority_to_queue_map_fld_xfmr";
      }
    }

    deviation /oc-qos:qos/oc-qos:interfaces/oc-qos:interface/oc-qos-maps-ext:interface-maps/oc-qos-maps-ext:state/oc-qos-maps-ext:forwarding-group-to-dscp {
      deviate add {
        sonic-ext:field-transformer "qos_tc_to_dscp_map_fld_xfmr";
      }
    }

    deviation /oc-qos:qos/oc-qos:interfaces/oc-qos:interface/oc-qos-maps-ext:interface-maps/oc-qos-maps-ext:state/oc-qos-maps-ext:forwarding-group-to-dot1p {
      deviate add {
        sonic-ext:field-transformer "qos_tc_to_dot1p_map_fld_xfmr";
      }
    }

    deviation /oc-qos:qos/oc-qos:forwarding-groups {
      deviate add {
          sonic-ext:table-name "NONE";
      }
    }

    deviation /oc-qos:qos/oc-qos:forwarding-groups/oc-qos:forwarding-group {
      deviate add {
          sonic-ext:key-transformer "qos_fwdgrp_tbl_key_xfmr";
          sonic-ext:table-transformer "qos_fwdgrp_table_xfmr";
      }
    }

    deviation /oc-qos:qos/oc-qos:forwarding-groups/oc-qos:forwarding-group/oc-qos:config/oc-qos:name {
      deviate add {
          sonic-ext:field-transformer "qos_fwdgrp_fld_xfmr";
      }
    }

    deviation /oc-qos:qos/oc-qos:forwarding-groups/oc-qos:forwarding-group/oc-qos:state/oc-qos:name {
      deviate add {
          sonic-ext:field-transformer "qos_fwdgrp_fld_xfmr";
      }
    }

///////////////////////// PFC Watchdog Interface ////////////////////////////////////////////////////////
    deviation /oc-qos:qos/oc-qos:interfaces/oc-qos:interface/oc-qos-ext:pfc/oc-qos-ext:pfc-priorities/oc-qos-ext:pfc-priority/oc-qos-ext:state/oc-qos-ext:statistics {
      deviate add {
        sonic-ext:subtree-transformer "qos_intf_pfc_counters_st_xfmr";
      }
    }

    deviation /oc-qos:qos/oc-qos:interfaces/oc-qos:interface/oc-qos-ext:pfc/oc-qos-ext:watchdog {
      deviate add {
        sonic-ext:table-name "PFC_WD";
        sonic-ext:subtree-transformer "qos_intf_pfcwd_st_xfmr";
      }
    }

    deviation /oc-qos:qos/oc-qos:interfaces/oc-qos:interface/oc-qos-ext:pfc/oc-qos-ext:watchdog/oc-qos-ext:config/oc-qos-ext:action {
      deviate add {
        sonic-ext:field-name "action";
        sonic-ext:field-transformer "qos_intf_pfcwd_action_fld_xfmr";
      }
    }

    deviation /oc-qos:qos/oc-qos:interfaces/oc-qos:interface/oc-qos-ext:pfc/oc-qos-ext:watchdog/oc-qos-ext:config/oc-qos-ext:detection-time {
      deviate add {
        sonic-ext:field-name "detection_time";
      }
    }

    deviation /oc-qos:qos/oc-qos:interfaces/oc-qos:interface/oc-qos-ext:pfc/oc-qos-ext:watchdog/oc-qos-ext:config/oc-qos-ext:restoration-time {
      deviate add {
        sonic-ext:field-name "restoration_time";
      }
    }

    deviation /oc-qos:qos/oc-qos:interfaces/oc-qos:interface/oc-qos-ext:pfc/oc-qos-ext:watchdog/oc-qos-ext:state/oc-qos-ext:action {
      deviate add {
        sonic-ext:field-name "action";
        sonic-ext:field-transformer "qos_intf_pfcwd_action_fld_xfmr";
      }
    }

    deviation /oc-qos:qos/oc-qos:interfaces/oc-qos:interface/oc-qos-ext:pfc/oc-qos-ext:watchdog/oc-qos-ext:state/oc-qos-ext:detection-time {
      deviate add {
        sonic-ext:field-name "detection_time";
      }
    }

    deviation /oc-qos:qos/oc-qos:interfaces/oc-qos:interface/oc-qos-ext:pfc/oc-qos-ext:watchdog/oc-qos-ext:state/oc-qos-ext:restoration-time {
      deviate add {
        sonic-ext:field-name "restoration_time";
      }
    }

    deviation /oc-qos:qos/oc-qos:interfaces/oc-qos:interface/oc-qos-ext:pfc/oc-qos-ext:pfc-queue/oc-qos-ext:pfc-queue/oc-qos-ext:statistics {
      deviate add {
        sonic-ext:db-name "COUNTERS_DB";
        sonic-ext:subtree-transformer "qos_intf_pfc_queue_counters_st_xfmr";
      }
    }

///////////////////////// PFC Watchdog Global ////////////////////////////////////////////////////////
  deviation /oc-qos:qos/oc-qos-ext:pfc-watchdog {
    deviate add {
      sonic-ext:table-name "NONE";
    }
  }

  deviation /oc-qos:qos/oc-qos-ext:pfc-watchdog/oc-qos-ext:flex {
    deviate add {
      sonic-ext:table-name "FLEX_COUNTER_TABLE";
      sonic-ext:key-transformer "flex_counter_key_xfmr";

    }
  }

  deviation /oc-qos:qos/oc-qos-ext:pfc-watchdog/oc-qos-ext:flex/oc-qos-ext:config/oc-qos-ext:counter-poll {
    deviate add {
      sonic-ext:field-name "FLEX_COUNTER_STATUS";
      sonic-ext:field-transformer "counter_poll_fld_xfmr";
    }
  }

  deviation /oc-qos:qos/oc-qos-ext:pfc-watchdog/oc-qos-ext:flex/oc-qos-ext:state/oc-qos-ext:counter-poll {
    deviate add {
      sonic-ext:field-name "FLEX_COUNTER_STATUS";
      sonic-ext:field-transformer "counter_poll_fld_xfmr";
    }
  }

  deviation /oc-qos:qos/oc-qos-ext:pfc-watchdog/oc-qos-ext:poll {
    deviate add {
      sonic-ext:table-name "PFC_WD";
      sonic-ext:key-transformer "poll_interval_key_xfmr";
    }
  }

  deviation /oc-qos:qos/oc-qos-ext:pfc-watchdog/oc-qos-ext:poll/oc-qos-ext:config/oc-qos-ext:poll-interval {
    deviate add {
      sonic-ext:field-name "POLL_INTERVAL";
    }
  }

  deviation /oc-qos:qos/oc-qos-ext:pfc-watchdog/oc-qos-ext:poll/oc-qos-ext:state/oc-qos-ext:poll-interval {
    deviate add {
      sonic-ext:field-name "POLL_INTERVAL";
    }
  }

}
