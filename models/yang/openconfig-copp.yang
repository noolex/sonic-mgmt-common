module openconfig-copp {

	yang-version "1";

	// namespace
	namespace "http://openconfig.net/yang/copp";

	prefix "oc-copp";

	import openconfig-extensions { prefix oc-ext; }

	// meta
	organization "OpenConfig working group";

	contact
		"OpenConfig working group
		www.openconfig.net";

	description
		"This module defines configuration and operational state
		data for control plane policing lists";

	oc-ext:openconfig-version "1.0.2";

	revision "2019-05-06" {
		description
			"Initial revision";
		reference "TBD";
	}

	// OpenConfig specific extensions for module metadata.
	oc-ext:regexp-posix;
	oc-ext:catalog-organization "openconfig";
	oc-ext:origin "openconfig";

	// typedef statements
	typedef copp-trap-action {
		type enumeration {
			enum DROP {
				description
					"Packet gets drop";
			}
			enum FORWARD {
				description
					"Packet is forwarded";
			}
			enum COPY {
				description
					"Packet is copied";
			}
			enum COPY_CANCEL {
				description
					"Packet is copied then canceled";
			}
			enum TRAP {
				description
					"Packet is trapped";
			}
			enum LOG {
				description
					"Packet is logged";
			}
			enum DENY {
				description
					"Packet is denied";
			}
			enum TRANSIT {
				description
					"Packet is in transit";
			}
		}
		description
			"The action taken by the CoPP for the packet";
	}

	typedef copp-meter-type {
		type enumeration {
			enum PACKETS {
				description
					"Packets are metered";
			}
			enum BYTES {
				description
					"Bytes are metered";
			}
		}
		description
			"Identifies the metering method used by CoPP entry";
	}

	typedef copp-mode {
		type enumeration {
			enum SR_TCM {
				description
					"RFC 2697, Single Rate Three color marker, CIR, CBS and PBS, G, Y and R";
			}
			enum TR_TCM {
				description
					"RFC 2698, Two Rate Three color marker, CIR, CBS, PIR and PBS, G, Y and R";
			}
			enum STORM {
				description
					"Storm control mode. Single Rate Two color CIR, CBS, G and R";
			}
		}
		description
			"Identifies the mode used by CoPP entry";
	}

	// grouping statements
	grouping copp-main-config {
		description
			"Config of copp";

		list copp-group {
			key "name";
			description
				"List of CoPP entries comprising an CoPP group";

			leaf name {
				type string;
				description
					"Control plane policing classifier group name";
			}
			leaf trap-priority {
				type uint16;
				description
					"Priority value";
			}
			leaf trap-action {
				type copp-trap-action;
				description
					"Trap action";
			}
			leaf queue {
				type uint8;
				description
					"CPU queue id";
			}
			leaf cir {
				type uint64;
				description
					"Committed information rate in bps or pps
					(packets per second) depending on meter-type. CIR
					is mandatory";
			}
			leaf cbs {
				type uint64;
				description
					"Committed bucket size in packets or bytes. The
					default value is 20% of the CIR. If configured by
					the user, it must be greater than or equal to CIR
					in packets or bytes.";
			}

			leaf pir {
				type uint64;
				description
					"Peak information rate in bps or pps. If
					configured by the user, it must be greater than
					CIR.";
			}
			leaf pbs {
				type uint64;
				description
					"Peak bucket size. The default value is 20% of the
					PIR value. If configured by the user, it must be
					greater than PIR and CBS value.";
			}
			leaf meter-type {
				type copp-meter-type;
				description
					"Meter type";
			}
			leaf mode {
				type copp-mode;
				description
					"Mode";
			}
			leaf green-action {
				type copp-trap-action;
				description
					"Green action";
			}
			leaf red-action {
				type copp-trap-action;
				description
					"Red action";
			}
			leaf yellow-action {
				type copp-trap-action;
				description
					"Yellow action";
			}
			leaf enable {
				type boolean;
				description
					"enable/disable classifier";
			}
		}
		list copp-trap {
			key "name";
			description
				"List of CoPP entries comprising an CoPP trap";

			leaf name {
				type string;
				description
					"Control plane policing classifier trap name";
			}
			leaf trap-ids {
				type string;
				description
					"Comma separated string of trap-ids";
			}
			leaf trap-group {
				type string;
				description
					"reference to CoPP group";
			}
		}
	}

	grouping copp-main-state {
		description
			"State information of interface";
	}

	grouping copp-main-top {
		description
			"Input top level container";

		container copp-config {
			description
				"Config data";
			uses copp-main-config;
		}

		container copp-state {
			config false;
			description
				"State information";
			uses copp-main-state;
		}

	}

	// data definition statements
	uses copp-main-top;

	// augment statements
}
