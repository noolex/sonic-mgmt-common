module sonic-qos-clear {
    namespace "http://github.com/Azure/sonic-qos-clear";
    prefix sqosclear;
    yang-version 1.1;

    import sonic-port {
        prefix prt;
    }

    organization
        "SONiC";

    contact
        "SONiC";

    description
        "SONiC yang for QOS clear options";

    revision 2020-04-06 {
        description
            "Initial revision.";
    }

   rpc clear-qos {

    description "RPC for clearing QOS Counters. Input can be :
        1. All Queues Counters 
        2. Per Interface,All Queue Counters 
        3. Per Interface Queue Counters 
        4. All unicast/multicast queues watermark/persistent-watermark counters 
        5. Per Interface unicast/multicast queues watermark/persistent-watermark counters 
        6. All headroom/shared queues watermark/persistent-watermark counters 
        7. Per Interface unicast/multicast queues watermark/persistent-watermark counters"; 

    input {

        leaf counter-type {
            mandatory true;    
            type enumeration {
                enum queue;
                enum priority-group;
            }
            description
                "QOS Counter type for clear.";
        }

        choice counter-options {
            mandatory true;    
            container counters {
                leaf wred {
                    type boolean;
                    default false;
                    description
                        "Clear WRED queues counters.";
               }
               choice clear-options {
                   mandatory true;    
                   leaf all {
                       type boolean;
                       description
                           "Clear all counters.";
                   }

                   leaf interface {
                       type union {
                           type leafref {
                               path "/prt:sonic-port/prt:PORT/prt:PORT_LIST/prt:ifname";
                           }
                           type string {
                               pattern "CPU";
                           }
                       }
                       description
                           "Interface name: Parameter for clearing all queues/pgs counters on
                           the given inteface name Valid inputs are: Ethernet<port-number>.
                           For example: Ethernet0";
                   }

                   leaf queue {
                       type string;
                       description
                           "Clear all queue counters.";
                       when "../../../counter-type='queue'" {
                        description
                            "Queue fields are valid when the counter type is queue";
                       }
                   }

                   leaf priority-group {
                       type string;
                       description
                           "Clear all priority-group counters.";
                       when "../../../counter-type='priority-group'" {
                          description
                            "PG type fields are valid when the Counter type is Priority-group";
                       }
                   }
               }
            }

            container watermarks {
                leaf persistent {
                    type boolean;
                    default false;
                    description
                        "Clear buffer persistent watermarks.";
                }

                leaf queue-type {
                    type enumeration {
                        enum unicast;
                        enum multicast;
                        enum both;
                    }
                    default both;
                    description
                        "Clear unicast/multicast queues buffer watermarks.";
                    when "../../../counter-type='queue'" {
                        description
                            "Queue fields are valid when the counter type is queue";
                    }
                }

                leaf pg-type {
                    type enumeration {
                        enum headroom;
                        enum shared;
                        enum both;
                    }
                    default both;
                    description
                        "Clear PG headroom/shared buffer watermarks.";
                    when "../../../counter-type='priority-group'" {
                        description
                            "PG type fields are valid when the Counter type is Priority-group";
                    }
                }

                choice clear-options {
                    mandatory true;    
                    leaf all {
                        type boolean;
                        description
                            "Clear all buffer watermarks.";
                    }

                    leaf interface {
                        type union {
                            type leafref {
                                path "/prt:sonic-port/prt:PORT/prt:PORT_LIST/prt:ifname";
                            }
                            type string {
                                pattern "CPU";
                            }
                        }

                        description
                            "Interface name: Parameter for deleting all interface queues/pg
                            buffer watermarks on the given inteface name Valid inputs are:
                            Ethernet<port-number>.
                            For example: Ethernet0";
                    }
                }
            }
        }
    }

    output {
        leaf status {
            type string;
            description
                "Success / failure in clearing QOS counters operation execution request.";
        }
    }
   }
}
