module sonic-switch-resource {
  namespace "http://github.com/Azure/sonic-switch-resource";
  prefix sswresource;
  yang-version 1.1;

  import sonic-extension {
    prefix sonic-ext;
  }

  import sonic-common {
      prefix cmn;
  }


  organization
    "SONiC";

  contact
    "SONiC";

  description
    "SONiC Switch Resource yang model";

  revision 2020-07-07 {
    description
      "Initial revision.";
  }

  typedef switch-resource-type {
    type enumeration {
      enum DROP_MONITOR {
        description
          "Drop Monitor Resource";
      }
      enum ROUTE_SCALE {
        description
          "Route Scale Resource";
      }
    }
    description
      "The Different Resource Types of Switch Resource Management  ";
  }


  typedef flow-scale-limit {
    type enumeration {
      enum "NONE" {
        description
          "No flow scale  configured.";
      }
      enum "MIN" {
        description
          "Minimum flow scale configured.";
      }
      enum "UNSUPPORTED" {
        description
          "flow scale not supported.";
      }
    }
    description
      "Drop Monitor Flow scale limit ";

  }

  typedef route-scale-limit {
    type enumeration {
      enum "DEFAULT" {
        description
          "No route scale configured.";
      }
      enum "MAX" {
        description
          "Maximum route scale configured.";
      }
    }
    description
      "Route scale limit ";

  }

  container sonic-switch-resource {
    container SWITCH_RESOURCE_TABLE {
      list SWITCH_RESOURCE_TABLE_LIST {
        key "name";

        leaf name {
          type switch-resource-type;
          description
            "Types of Switch Resources";
        }


        leaf flows {
          type flow-scale-limit;
          must 'not(current()/../../SWITCH_RESOURCE_TABLE_LIST[name="ROUTE_SCALE"]/routes) or' +
               '(current()/../../SWITCH_RESOURCE_TABLE_LIST[name="ROUTE_SCALE"]/routes = "DEFAULT")'
          {
              error-message "Remove route-scale configuration before configuring drop-monitor flows";
              error-app-tag switch-resouce-invalid-config;
          }
          sonic-ext:custom-validation IsDropMonitorSupported;
          description
            "Drop Monitor Flow scale options ";
        }

        leaf routes {
          type route-scale-limit;
          must 'not(current()/../../SWITCH_RESOURCE_TABLE_LIST[name="DROP_MONITOR"]/flows) or' +
               '(current()/../../SWITCH_RESOURCE_TABLE_LIST[name="DROP_MONITOR"]/flows = "NONE")'
          {
              error-message "Remove drop-monitor configuration before configuring route-scale";
              error-app-tag switch-resouce-invalid-config;
          }
          description
            "Route scale options ";
        }

      }
    }

    container SWITCH_RESOURCE_STATE_TABLE {

      sonic-ext:db-name "COUNTERS_DB";
      sonic-ext:key-delim ":";

      config false;
      description "state switch resource table";

      list SWITCH_RESOURCE_STATE_TABLE_LIST {
        key "name";

        leaf name {
          type switch-resource-type;
          description
            "Types of Switch Resources";
        }


        leaf flows_in_hardware {
          type flow-scale-limit;
          description
            "Shows user-configured flow scale when the system boots up ";
        }
      }
    }
  }
}
