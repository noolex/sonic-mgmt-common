module sonic-system-dns {
    namespace "http://github.com/Azure/sonic-system-dns";
    prefix ssys;
    yang-version 1.1;

    import ietf-inet-types {
        prefix inet;
    }

    import sonic-port {
        prefix prt;
    }

    import sonic-portchannel {
        prefix spc;
    }

    import sonic-vlan {
        prefix svlan;
    }

    import sonic-loopback {
        prefix lo;
    }

    import sonic-interface {
        prefix sintf;
    }

    import sonic-mgmt-port {
        prefix smt;
    }
 
    revision 2021-01-08 {
        description "Added support for routed vlan-sub-interface.";
    }

    revision 2020-08-20 {
        description
            "Add vrf-name for DNS server.";
    } 
  
    revision 2020-07-26 {
        description
            "Change for sonic-loopback.yang.";
    } 
    revision 2020-05-02 {
        description "Initial revision.";
    }

    container sonic-system-dns {

        container DNS_SERVER {
            list DNS_SERVER_LIST {
                key "ipaddress";
                max-elements 6;

                leaf ipaddress {
                    type inet:ip-address;
                }

                leaf vrf_name {
                    type string {
                        pattern "mgmt|default";
                    }
                }
            }
        }

        container DNS {
            list DNS_LIST {

                key "type";

                leaf type {
                    type enumeration {
                        enum global;
                    }
                }

                leaf src_intf {
                    type union {
                        type leafref {
                            path "/prt:sonic-port/prt:PORT/prt:PORT_LIST/prt:ifname";
                        }
                        type leafref {
                            path "/spc:sonic-portchannel/spc:PORTCHANNEL/spc:PORTCHANNEL_LIST/spc:name";
                        }
                        type leafref {
                            path "/svlan:sonic-vlan/svlan:VLAN/svlan:VLAN_LIST/svlan:name";
                        }
                        type leafref {
                            path "/lo:sonic-loopback/lo:LOOPBACK/lo:LOOPBACK_LIST/lo:name";
                        }
                        type leafref {
                            path "/smt:sonic-mgmt-port/smt:MGMT_PORT/smt:MGMT_PORT_LIST/smt:ifname";
                        }
                        type leafref {
                            path "/sintf:sonic-interface/sintf:VLAN_SUB_INTERFACE/sintf:VLAN_SUB_INTERFACE_LIST/sintf:id";
                        }
                    }
                }
            }
        }
    }
}
