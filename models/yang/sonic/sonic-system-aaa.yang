module sonic-system-aaa {
    namespace "http://github.com/Azure/sonic-system-aaa";
    prefix ssys;
    yang-version 1.1;

    revision 2020-07-30 {
        description "Adding User container for USERNAME.";
    }

    revision 2020-06-08 {
        description "AAA Name Service.";
    }

    revision 2019-11-13 {
        description "Initial revision.";
    }

    container sonic-system-aaa {
        container AAA {
            list AAA_LIST {
                key "type";

                leaf type {
                    type enumeration {
                        enum authentication;
                        enum authorization;
                        enum nss;
                    }
                }

                leaf login {
                    type string;
                }

                leaf passwd {
                    type string;
                }

                leaf shadow {
                    type string;
                }

                leaf group {
                    type string;
                }

                leaf netgroup {
                    type string;
                }

                leaf sudoers {
                    type string;
                }

                leaf failthrough {
                    type string {
                        pattern "True|False" {
                            error-message "Error: Invalid failthrough setting";
                        }
                    }
                }
            }
        }
        container USER {
            list USER_LIST {
                key "username";

                leaf username {
                    type string {
                        pattern '[a-z_][a-z0-9_-]*[$]';
                        length 1..31;
                    }
                }

                leaf password {
                    type string;
                    description "Hashed password for username.";
                }

                leaf-list role {
                    type string;
                    description "Role of the user [admin/operator].";
                }
            }
        }
    }
}
