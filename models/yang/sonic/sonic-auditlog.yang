module sonic-auditlog {
    namespace "http://github.com/Azure/sonic-auditlog";
    prefix auditlog;
    yang-version 1.1;

    organization
        "SONiC";

    contact
        "SONiC";

    description
        "SONiC yang for audit log.";

    revision 2020-05-29 {
        description
            "Initial revision.";
    }

    rpc get-auditlog {
       description "RPC for getting audit log.";

       input {
           leaf content-type {
               type string {
                   pattern "all";
               }
               description "Indicates if user wants to get all or latest twenty lines of audit log";
           }
       }

       output {
           list audit-content {
               leaf content {
                   type string;
                   description "Audit message";
               }
           }
       }
    }

    rpc clear-auditlog {
       description "RPC for clearing audit log.";

       output {
           leaf status {
               type string;
               description "Clear operation status";
           }
       }
    }
}
