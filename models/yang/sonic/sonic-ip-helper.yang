module sonic-ip-helper {
  namespace "http://github.com/Azure/sonic-ip-helper";
  prefix ip-helper;
  yang-version 1.1;

  import sonic-extension {
    prefix sonic-ext;
  }

  organization
    "SONiC";

  contact
    "SONiC";

  description
    "SONiC IP-Helper yang model";

  revision 2020-06-04 {
    description
      "Initial revision";
  }

  grouping ip_helper_config {
    leaf admin_mode {
      type string {
        pattern 'disable|enable';
      }
      default 'disable';
    }
    leaf rate_limit_pps {
      type uint16 {
        range "600..10000" {
          error-message "Value should be between 600 and 10000";
        } 
      }
      default 600;
    }
    leaf-list include_ports {
      type uint16;
    }
    leaf-list exclude_default_ports {
      type uint16;
    }
  }

  grouping ip_helper_interface_counters {

    leaf PKTS_RECEIVED {
      type uint64;
    }
    leaf PKTS_RELAYED {
      type uint64;
    }
    leaf PKTS_DROPPED {
      type uint64;
    }
    leaf PKTS_INVALID_TTL {
      type uint64;
    }
    leaf PKTS_BROADCAST {
      type uint64;
    }
    leaf PKTS_NET_BROADCAST {
      type uint64;
    }
  }


  container sonic-ip-helper {

    container UDP_BROADCAST_FORWARDING {
      list UDP_BROADCAST_FORWARDING_LIST {
        key "id";

        leaf id {
          type enumeration {
            enum Ports;
          }
          description
            "It's value is always Ports";
        }

        uses ip_helper_config;

      }
    }

    container COUNTERS_IP_HELPER {
      sonic-ext:db-name "COUNTERS_DB";
      sonic-ext:key-delim ":";
      list COUNTERS_IP_HELPER_LIST {
        key "interface";

        leaf interface {
          type string;
          description
            "It's value is id of the interface";
        }

        uses ip_helper_interface_counters;

      }
    }

  }

  rpc clear-ip-helper-statistics{
    input {
      leaf interface {
        type string;
      }
    }
    output {
      leaf error {
        type string;
      }
    }
  }
}
