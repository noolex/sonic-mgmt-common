module sonic-audit-log {
    namespace "http://github.com/Azure/sonic-audit-log";
    prefix auditshow;
    yang-version 1.1;

    organization
        "SONiC";

    contact
        "SONiC";

    description
        "SONiC yang for RPC based show audit log.";

    revision 2020-05-29 {
        description
            "Initial revision.";
    }

    rpc show-audit-log {
       description "RPC for showing audit log.";

       output {
           leaf content {
               type string;
               description "First 100 lines of audit log";
           }
       }
    }
}
