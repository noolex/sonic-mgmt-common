module sonic-tam-dropmonitor {
    yang-version 1.1;

    // namespace
    namespace "http://github.com/Azure/sonic-tam-dropmonitor";

    prefix sonic-tam-dropmonitor;

    import sonic-acl {
        prefix sonic-acl;
    }

    import sonic-tam-collectors {
        prefix sonic-tam-collectors;
    }

    import sonic-tam-samplers {
        prefix sonic-tam-samplers;
    }

    import sonic-extension {
        prefix sonic-ext;
    }

    // meta
    organization
      "SONiC";

    contact
      "SONiC";

    description
      "Silicon Telemetry Module";

    revision 2020-06-01 {
        description
          "Initial revision";
        reference
          "3.2.0";
    }

    // extension statements
    // feature statements
    // identity statements
    // typedef statements
    // grouping statements
    // data definition statements
    container sonic-tam-dropmonitor {
        description
          "top-level container";

        container TAM_DROPMONITOR_TABLE {
            description
              "tam-switch table in the config-db";

            list TAM_DROPMONITOR_TABLE_LIST {
                key name;

                description
                  "switch-wide attributes";

                leaf name {
                    type enumeration {
                        enum global {
                            description
                              "Global key";
                        }
                    }
                    description
                      "Global switch-wide attributes";
                }
                leaf aging-interval {
                    type uint16 {
                        range 1..30;
                    }
                    units "seconds";
                    default 5;
                    description
                      "Interval in seconds for aging out flows";
                }
            }
        }

        container TAM_DROPMONITOR_SESSIONS_TABLE {
            description
              "tam-dropmonitor-sessions table in the config-db";

            list TAM_DROPMONITOR_SESSIONS_TABLE_LIST {
                key name;

                sonic-ext:custom-validation DropMonitorSessionValidation;
                description
                  "Individual sessions configuration";

                leaf name {
                    type string {
                        length "1..32";
                        pattern
                          '[a-zA-Z0-9]{1}([-a-zA-Z0-9_]{0,32})';
                    }
                    mandatory true;
                    description
                      "Session name, for reference from elsewhere";
                }

                leaf flowgroup {
                    type string {
                        length "1..32";
                        pattern
                          '[a-zA-Z0-9]{1}([-a-zA-Z0-9_]{0,32})';
                    }
                    must "(/sonic-acl:sonic-acl/sonic-acl:ACL_RULE/sonic-acl:ACL_RULE_LIST/sonic-acl:rulename = current())" {
                        error-message "Flowgroup does not exists";
                        error-app-tag flowgroup-not-exists;
                    }
                    mandatory true;
                    description
                      "Flowgroup name";
                }

                leaf collector {
                    type string {
                        length "1..32";
                        pattern
                          '[a-zA-Z0-9]{1}([-a-zA-Z0-9_]{0,32})';
                    }
                    must "(/sonic-tam-collectors:sonic-tam-collectors/sonic-tam-collectors:TAM_COLLECTORS_TABLE/sonic-tam-collectors:TAM_COLLECTORS_TABLE_LIST/sonic-tam-collectors:name = current())" {
                        error-message "Collector does not exists";
                        error-app-tag collector-not-exists;
                    }
                    mandatory true;
                    description
                      "Collector to be used for DROPMONITOR for this session";
                }

                leaf sample-rate {
                    type string {
                        length "1..32";
                        pattern
                          '[a-zA-Z0-9]{1}([-a-zA-Z0-9_]{0,32})';
                    }
                    must "(/sonic-tam-samplers:sonic-tam-samplers/sonic-tam-samplers:TAM_SAMPLINGRATE_TABLE/sonic-tam-samplers:TAM_SAMPLINGRATE_TABLE_LIST/sonic-tam-samplers:name = current())" {
                        error-message "Sampler does not exists";
                        error-app-tag sampler-not-exists;
                    }
                    mandatory true;
                    description
                      "Sample-rate to be used for DROPMONITOR for this session";
                }
            }
        }
    }
// augment statements
// rpc statements
// notification statements
}
