module sonic-tam-features {
    yang-version 1.1;

    // namespace
    namespace "http://github.com/Azure/sonic-tam-features";

    prefix sonic-tam-features;

    // import some basic types
    import sonic-tam-types {
        prefix sonic-tam-type;
    }

    import sonic-extension {
        prefix sonic-ext;
    }

    // meta
    organization
      "SONiC";

    contact
      "SONiC";

    description
      "Silicon Telemetry Module";

    revision 2020-06-01 {
        description
          "Initial revision";
        reference
          "3.2.0";
    }

    // extension statements
    // feature statements
    // identity statements
    // typedef statements
    // grouping statements
    // data definition statements
    container sonic-tam-features {
        description
          "top-level container";

        container TAM_FEATURES_TABLE {
            description
              "tam-features table in the config-db";

            list TAM_FEATURES_TABLE_LIST {
                key feature-ref;

                description
                  "Individual features configuration";

                leaf feature-ref {
                    type enumeration {
                        enum IFA {
                            description
                              "Inband Flow Analyzer";
                        }
                        enum DROPMONITOR {
                            description
                              "Drop Monitor";
                        }
                        enum TAILSTAMPING {
                            description
                              "Tail Stamping";
                        }
                    }
                    mandatory true;
                    description
                      "Collector name, for reference from elsewhere";
                }
                leaf status {
                    type sonic-tam-type:tam-feature-status-type;
                    must "((current() = 'ACTIVE') or (current() = 'INACTIVE'))" {
                        error-message
                          "Status should be either ACTIVE or INACTIVE";
                        error-app-tag
                          tam-feature-invalid-status;
                    }
                    sonic-ext:custom-validation ValidateFeatureStatus;
                    mandatory true;
                    description
                      "Allows configuring the feature to be turned on or off";
                }
            }
        }

        container TAM_STATE_FEATURES_TABLE {

            config false;

            description
              "tam-features table in the appl-db";

            sonic-ext:db-name "STATE_DB";
            sonic-ext:key-delim ":";

            list TAM_STATE_FEATURES_TABLE_LIST {
                key feature-ref;

                description
                  "Individual features configuration";

                leaf feature-ref {
                    type enumeration {
                        enum IFA {
                            description
                              "Inband Flow Analyzer";
                        }
                        enum DROPMONITOR {
                            description
                              "Drop Monitor";
                        }
                        enum TAILSTAMPING {
                            description
                              "Tail Stamping";
                        }
                    }
                    description
                      "Collector name, for reference from elsewhere";
                }
                leaf op-status {
                    type sonic-tam-type:tam-feature-status-type;
                    description
                      "Current operation status of the features";
                }
            }
        }
    }
// augment statements
// rpc statements
// notification statements
}
