module sonic-port-breakout {
    namespace "http://github.com/Azure/sonic-port-breakout";
    prefix sbrkprt;

    import sonic-port {
        prefix prt;
    }

    import sonic-extension {
        prefix sonic-ext;
    }

    organization
        "SONiC";

    contact
        "SONiC";

    description
        "SONiC Port Breakout";

    revision 2020-03-12 {
        description
            "Initial revision.";
    }

    container sonic-port-breakout {

        container BREAKOUT_CFG {

            list BREAKOUT_CFG_LIST {

                key "ifname";

                leaf ifname {
                    sonic-ext:custom-validation ValidateDpbConfigs;
                    type string {
                        pattern "Ethernet([1-3][0-9]{3}|[1-9][0-9]{2}|[1-9][0-9]|[0-9])";
                    }
                }

                leaf port {
                    type string;
                }

                leaf brkout_mode {
                    type enumeration {
                        enum 1x400G { value 1; }
                        enum 1x100G { value 2; }
                        enum 1x40G { value 3; }
                        enum 2x100G { value 4; }
                        enum 2x50G { value 5; }
                        enum 4x25G { value 6; }
                        enum 4x10G { value 7; }
                        enum 2x200G { value 8; }
                        enum 4x100G { value 9; }
                        enum 4x50G { value 10; }
                        enum 8x50G { value 11; }
                        enum 8x25G { value 12; }
                        enum 8x10G { value 13; }
                    }
                }
                leaf lanes {
                    type string;
                }
            }
        }

        container BREAKOUT_PORTS {

            list BREAKOUT_PORTS_LIST {

                key "ifname";

                leaf ifname {
                    type string {
                        pattern "Ethernet([1-3][0-9]{3}|[1-9][0-9]{2}|[1-9][0-9]|[0-9])";
                    }
                }

                leaf master {
                    type string;
                }
            }
        }

        container PORT_BREAKOUT {
            sonic-ext:db-name "STATE_DB";
            sonic-ext:key-delim "|";
            config false;
            list PORT_BREAKOUT_LIST {
                key "ifname";
                leaf ifname {
                    type string {
                        pattern "Ethernet([1-3][0-9]{3}|[1-9][0-9]{2}|[1-9][0-9]|[0-9])";
                    }
                }

                leaf status {
                    type string;
                }
            }
        }
    }

    rpc breakout_dependencies {

        description "RPC for showing dependencies on breakout port
        input is Ethernet interface";

        input {
            leaf ifname {
                type leafref {
                    path "/prt:sonic-port/prt:PORT/prt:PORT_LIST/prt:ifname";
                }
            }
        }

        output {
            leaf-list keys {
                type string;
                description
                    "On success, returns list of dependent table keys";
            }
        }
    }

    rpc breakout_capabilities {

        description "RPC for listing the breakout capabilities of ports
        input is Ethernet interface";

        input {
            leaf ifname {
                type leafref {
                    path "/prt:sonic-port/prt:PORT/prt:PORT_LIST/prt:ifname";
                }
            }
        }

        output {
            list caps {
                leaf port {
                    type string;
                }
                leaf modes {
                    type string;
                }
                leaf defmode {
                    type string;
                }
            }
        }
    }
}
