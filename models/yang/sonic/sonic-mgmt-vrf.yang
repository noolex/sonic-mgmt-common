module sonic-mgmt-vrf {
    namespace "http://github.com/Azure/sonic-mgmt-vrf";
    prefix mgmt-vrf;

    import sonic-extension {
        prefix sonic-ext;
    }

    organization
        "SONiC";

    contact
        "SONiC";

    description
        "SONIC MGMT VRF";

    revision 2020-09-14 {
        description
            "Only allow 1 entry in MGMT VRF TABLE,
             and the only key allowed is vrf_global";
    }

    revision 2020-07-14 {
        description
            "Support for in-band management via mgmt VRF.";
    }

    revision 2019-10-08 {
        description
            "Initial revision.";
    }

    container sonic-mgmt-vrf {
        container MGMT_VRF_CONFIG {
            description "Management vrf configuration.";            

            list MGMT_VRF_CONFIG_LIST {
                key "vrf_global_name";
                max-elements 1;

                leaf vrf_global_name {
                    type enumeration {
                        enum vrf_global;
                    }
 
                    description
                        "Internal management vrf name for SONiC";
                }   

                leaf mgmtVrfEnabled {
                    type  boolean;
                    default false;
                    description
                        "State indicating if management vrf is configured.";
                }

                leaf in_band_mgmt_enabled {
                    type  boolean;
                    default false;
                    description
                        "This is set to true when data interfaces are associated with management VRF for in-band management";
                }

                sonic-ext:custom-validation ValidateBeforeMgmtVrfDelete;
            }
        }
    }
}
