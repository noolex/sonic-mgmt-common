module sonic-tam-drop-monitor {
    namespace "http://github.com/Azure/sonic-tam-drop-monitor";
    prefix drop-monitor;

    import ietf-yang-types {
	    prefix yang;
    }

    import sonic-common {
	    prefix cmn;
    }

    import sonic-extension {
            prefix sonic-ext;
    }

    organization
        "SONiC";

    contact
        "SONiC";

    description
        "SONIC TAM DROP MONITOR YANG";

    revision 2020-07-01 {
        description
            "Added leaf string length correction changes for YANG module.";
    }

    revision 2019-11-28 {
        description
            "Initial revision.";
    }

    container sonic-tam-drop-monitor {

	container TAM_DROP_MONITOR_FEATURE_TABLE {

	    description
	       "Enable Drop Monitor Feature.";


            list TAM_DROP_MONITOR_FEATURE_TABLE_LIST {
                key "name";
	        description
	            "Feature Table List to enable Drop-Monitor feature.";

	        sonic-ext:custom-validation ValidateTAMFeature;

                leaf name {
                    type enumeration {
                        enum feature;
                    }

		    description
		       "Feature Table key name.";
                }

                leaf enable {
                    type boolean;

		    description
		       "Feature Table enable flag.";
                }
            }
        }
    

        container TAM_DROP_MONITOR_AGING_INTERVAL_TABLE {

		list TAM_DROP_MONITOR_AGING_INTERVAL_TABLE_LIST {
			key "name";
		        description
			  "Configures an aging-interval for drop-monitor flows configured in the system. 
                           The aging interval determines how long the system waits before it decides that drops have ceased on a flow.";

	                sonic-ext:custom-validation ValidateTAMFeature;

			leaf name {
				type enumeration {
					enum aging;
				}

				description
				     "Aging Table key name.";
			}

			leaf aging-interval {
				type uint16 {
					range "1..30" {
						error-message "Drop monitor aging interval is out of range";
						error-app-tag drop-monitor-aging-invalid;
					}

				}

                                description
			                 "Aging Interval defines the duration the switch waits to sends Drop-stop report to the collector after the drop event ceases on a flow.";
				default 3;
			}
		}
	}

	container SAMPLE_RATE_TABLE {

		list SAMPLE_RATE_TABLE_LIST {
			key "name";
		        description
			  "Create a sample session that co-relates a sampling rate with a session name.";

			leaf name {
				type string {
					pattern '[a-zA-Z0-9]{1}([-a-zA-Z0-9_]{0,71})';
					length 1..72;
				}

				description
				     "The sample session is identified by the name and can be used by multiple features to indicate sampling configuration.";
			}

			leaf sampling-rate {
				type uint16 {
					range "1..65535"{
				                error-message "Sampling-rate is out of range";
						error-app-tag "Invalid Drop Monitor Sampling Rate.";
					}
				}

				description
				     "One packet in every sampling rate packets will be sampled..";
			}
		}
	}

        container TAM_DROP_MONITOR_FLOW_TABLE {

            list TAM_DROP_MONITOR_FLOW_TABLE_LIST {
                key "name";
		description
		       "Associates a flow configuration (specified by the ACL table and ACL rule) with a collector, sampling configuration and flowgroup-id.";

	        sonic-ext:custom-validation ValidateTAMFeature;

                leaf name {
			type string {
				pattern '[a-zA-Z0-9]{1}([-a-zA-Z0-9_]{0,71})';
				length 1..72;

			}

		        description
			        "Name of the flow. It should be unique.";
                }

                leaf acl-table-name {
			mandatory true;
			type string {
				pattern '[a-zA-Z0-9]{1}([-a-zA-Z0-9_]{0,31})';
				length 1..32;
			}

		        description
			        "Parameter to map acl table to the flow.";
                }

                leaf acl-rule-name {
			mandatory true;
			type string {
				pattern '[a-zA-Z0-9]{1}([-a-zA-Z0-9_]{0,31})';
				length 1..32;
			}

		        description
			        "Parameter to map acl rule to the flow.";
                }

		leaf sample {
			type string {
				pattern '[a-zA-Z0-9]{1}([-a-zA-Z0-9_]{0,31})';
				length 1..32;
			}

		        description
			        "Map sampling rate configuration to the flow.";
		}

		leaf collector-name {
			type string {
				pattern '[a-zA-Z0-9]{1}([-a-zA-Z0-9_]{0,31})';
				length 1..32;
			}

		        description
			        "Map collector to the flow.";
		}

		leaf flowgroup-id {
			type uint16 {
				range "1..254"{
					error-app-tag "Invalid Flow Group Identifier.";
			}
			}
			must "(/cmn:operation/cmn:operation != 'CREATE') or (count(../../TAM_DROP_MONITOR_FLOW_TABLE_LIST[acl-table-name=current()/../acl-table-name and  acl-rule-name=current()/../acl-rule-name]/flowgroup-id) = 1)" {
				error-app-tag "invalid-flowgroup-id";
				error-message "Only single flowgroup-id is allowed for unique ACL table and rule combination";
			}
			must "(/cmn:operation/cmn:operation != 'UPDATE') or (count(../../TAM_DROP_MONITOR_FLOW_TABLE_LIST[acl-table-name=current()/../acl-table-name and  acl-rule-name=current()/../acl-rule-name]/flowgroup-id) <= 2)" {
				error-app-tag "invalid-flowgroup-id";
				error-message "Only single flowgroup-id is allowed for unique ACL table and rule combination";
			}

		        description
			        "Flow group ID. Must be unique per flow.";
		}

		container state {
			sonic-ext:db-name "COUNTERS_DB";
                        sonic-ext:key-delim ":";

			config false;
			description "State data for Drop Monitor Flow";


			leaf MATCHED_PACKETS {
				type yang:counter64;
                                default 0;

		                description
			            "Count of the number of packets matching the current ACL entry.";
			}

			leaf MATCHED_OCTETS {
				type yang:counter64;
                                default 0;

		                description
			            "Count of the number of octets (bytes) matching the current ACL entry.";
			}
		}

            }
        }
    }
}
