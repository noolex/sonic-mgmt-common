module sonic-coredump {
    namespace "http://github.com/Azure/sonic-coredump";
    prefix cdump;
    yang-version 1.1;

    organization
        "SONiC";

    contact
        "SONiC";

    description
        "This module contains a collection of YANG definitions for the
         Linux systemd-coredump application core dump utility. The systemd-coredump
         feature is used to detect and acquire information about application crash events
         in the system.";

    revision 2020-07-16 {
        description
            "Initial revision.";
    }

    grouping coredump_mode_config {
        description
            "Top level grouping for attributes for systemd-coredump";
        leaf enabled {
            type boolean;
            description
                "Enable or Disable the application systemd-coredump mechanism";
        }
    }

    container sonic-coredump {
        container COREDUMP {
            description
                "systemd-coredump configuration parameters";
            list COREDUMP_LIST {
                key "id";

                leaf id {
                    type enumeration {
                        enum config;
                    }
                    description
                        "Table identifier. It's value is always config";
                }
                uses coredump_mode_config;
            }
        }
    }
}
