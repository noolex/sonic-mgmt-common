module sonic-lldp {
    namespace "http://github.com/Azure/sonic-lldp";
    prefix slldp;
    yang-version 1.1;

    import sonic-port {
        prefix prt;
    }

    import sonic-extension {
        prefix sonic-ext;
    }

    import ietf-yang-types {
        prefix ietf-yang;
    }

    organization
        "SONiC";

    contact
        "SONiC";

    description
        "SONiC LLDP yang model";

    revision 2020-04-16 {
        description
            "Initial revision.";
    }

    grouping lldp_mode_config {
		leaf enabled {
			type boolean;
			description
				"Enable/Disable LLDP";
		}

		leaf mode {
			type enumeration {
				enum RECEIVE;
				enum TRANSMIT;
			}
			
			description
				"RX/TX mode for LLDP frames";
		}
    }

    container sonic-lldp {
        container LLDP {
            list LLDP_LIST {
                key "id";

                leaf id {
                    type enumeration {
                        enum GLOBAL;
                    }
                    description
                        "It's value is always GLOBAL";
                }


                leaf hello_time {
                    type uint8 {
                        range "5..254" {
                            error-message "Invalid hello timer value.";
                        }
                    }
                    units seconds;
                    description
                        "It is the time interval at which periodic hellos are
                        exchanged. Default is 30 seconds";
                }

                leaf multiplier {
                    type uint8 {
                        range "1..10" {
                            error-message "Invalid LLDP multiplier value.";
                        }
                    }
                    description
                        "This multiplier value is used to determine the timeout
                        interval (i.e. hello-time x multiplier value) after
                        which LLDP neighbor entry is deleted.";
                }

				leaf system_name {
					type string;
					description
						"System administratively assigned name";
				}

				leaf system_description {
					type string;
					description
						"System description";
				}

				leaf supp_mgmt_address_tlv {
					type boolean;
					description
						"Suppress sending of Management Address TLV in LLDP frames";
				}

				leaf supp_system_capabilities_tlv {
					type boolean;
					description
						"Suppress sending of System Capabilities TLV in LLDP frames";
				}

                uses lldp_mode_config;
            }
        }

        container LLDP_PORT {
            list LLDP_PORT_LIST {
                key "ifname";

                leaf ifname {
                    type leafref {
                        path "/prt:sonic-port/prt:PORT/prt:PORT_LIST/prt:ifname";
                    }
                    description
                        "Reference of port on which LLDP to be configured.";
                }

                uses lldp_mode_config;
            }
        }

        container LLDP_PORT_TABLE {
            config false;

            list LLDP_PORT_TABLE_LIST {
                sonic-ext:db-name "APPL_DB";
                key "ifname";

                leaf ifname {
                    type leafref {
                        path "/prt:sonic-port/prt:PORT/prt:PORT_LIST/prt:ifname";
                    }
                    description
                        "Reference of port on which LLDP is configured.";
                }

                leaf rx {
                    type ietf-yang:counter64;
                    description
                        "The number of lldp frames received";
                }

                leaf tx {
                    type ietf-yang:counter64;
                    description
                        "The number of lldp frames transmitted out";
                }

                leaf rx_discarded_cnt {
                    type ietf-yang:counter64;
                    description
                        "The number of lldp frames received and discarded";
                }

                leaf rx_unrecognized_cnt {
                    type ietf-yang:counter64;
                    description
                        "The number of frames received with unknown TLV";
                }

                leaf ageout_cnt {
                    type ietf-yang:counter64;
                    description
                        "Indicates number of times neighbor aged out";
                }
            }
        }
    }
}
