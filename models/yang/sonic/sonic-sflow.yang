module sonic-sflow {
    namespace "http://github.com/Azure/sonic-sflow";
    prefix sflow;
    yang-version 1.1;

    import ietf-inet-types {
        prefix inet;
    }

    import sonic-common {
        prefix scommon;
    }
    import sonic-port {
        prefix prt;
    }
    import sonic-vlan {
        prefix svlan;
    }
    import sonic-loopback {
        prefix lo;
    }
    import sonic-mgmt-port {
        prefix smt;
    }

    revision 2020-07-26 {
        description
            "Change for sonic-loopback.yang.";
    }

    revision 2020-06-23 {
        description
            "Add default and mgmt VRF.
             Increase collector name to 32 characters.";
    }

    revision 2019-09-09 {
        description
            "Initial revision.";
    }

    container sonic-sflow {
        container SFLOW_COLLECTOR {
            list SFLOW_COLLECTOR_LIST {
                max-elements 2;
                key "collector_name";

                leaf collector_name {
                    type string {
                        length 1..64;
                    }
                }

                leaf collector_ip {
                    mandatory true;
                    type inet:ip-address;
                }


                leaf collector_port {
                    type inet:port-number;
                }

                leaf collector_vrf {
                    type string {
                            pattern "default|mgmt";
                    }
                    description "Network-instance/VRF name";
                }

            }
        }

        container SFLOW_SESSION {
            list SFLOW_SESSION_LIST {
                key "ifname";

                leaf ifname {
                    type leafref {
                        path "/prt:sonic-port/prt:PORT/prt:PORT_LIST/prt:ifname";
                    }
                }

                leaf admin_state {
                    type scommon:admin-status;
                }

                leaf sample_rate {
                    type uint32 {
                        range "256..8388608" {
                            error-message "sFlow polling interval must be [256-8388608]";
                        }
                    }
                }
            }
        }

        container SFLOW {
            list SFLOW_LIST {
                key "sflow_key";
                leaf sflow_key {
                    type enumeration {
                        enum global;
                    }
                }

                leaf admin_state {
                    type scommon:admin-status;
                }

                leaf polling_interval {
                    type uint16 {
                        range "0|5..300" {
                            error-message "sFlow sample rate must be [0, 5-300]";
                        }
                    }
                }

                leaf agent_id {
                    type union {
                        type leafref {
                            path "/prt:sonic-port/prt:PORT/prt:PORT_LIST/prt:ifname";
                        }
                        type leafref {
                            path "/smt:sonic-mgmt-port/smt:MGMT_PORT/smt:MGMT_PORT_LIST/smt:ifname";
                        }
                        type leafref {
                            path "/svlan:sonic-vlan/svlan:VLAN/svlan:VLAN_LIST/svlan:name";
                        }
                        type leafref {
                            path "/lo:sonic-loopback/lo:LOOPBACK/lo:LOOPBACK_LIST/lo:name";
                        }
                    }
                    description "Interface name";
                }
            }
       }

       container SFLOW_SESSION_TABLE {
           config false;
           list SFLOW_SESSION_TABLE_LIST {
               key "ifname";

               leaf ifname {
                   type leafref {
                       path "/prt:sonic-port/prt:PORT/prt:PORT_LIST/prt:ifname";
                   }
               }

               leaf admin_state {
                   type scommon:admin-status;
               }

               leaf sample_rate {
                   type uint32 {
                       range "256..8388608" {
                           error-message "sFlow polling interval must be [256-8388608]";
                       }
                   }
               }
           }
       }
    }
}
