module sonic-tam-int-ifa-ts {
    namespace "http://github.com/Azure/sonic-tam-int-ifa-ts";
    prefix stam-ts;

    import ietf-yang-types {
        prefix yang;
    }

    import sonic-extension { 
            prefix sonic-ext; 
    }

    organization
        "SONiC";

    contact
        "SONiC";

    description
         "This module defines configuration and operational state
          data for IFA TailStamping Feature."; 

    revision 2020-07-01 {
        description
            "Added leaf string length correction changes for YANG module.";
    }

    revision 2019-11-14 {
        description
            "Initial revision.";
    }

    container sonic-tam-int-ifa-ts {

        container TAM_INT_IFA_TS_FEATURE_TABLE {

            list TAM_INT_IFA_TS_FEATURE_TABLE_LIST {
                key "name";
	        sonic-ext:custom-validation ValidateTAMFeature;

                leaf name {
                        type string {
                                pattern 'feature';
                        }
                        description
                            "Feature identifier name in IFA TailStamping feature table.";
                }

                leaf enable {
                    type boolean;
                    default false;
                    description
                        "Flag to enable or disable IFA TailStamping feature.";
                }
            }
        }

        container TAM_INT_IFA_TS_FLOW_TABLE {

            list TAM_INT_IFA_TS_FLOW_TABLE_LIST {
                key "name";
	        sonic-ext:custom-validation ValidateTAMFeature;

                leaf name {
                        type string {
                                pattern '[a-zA-Z0-9]{1}([-a-zA-Z0-9_]{0,71})'{
                                   error-message "Invalid INT IFA TS Flow name";
                                   error-app-tag int-ifa-ts-invalid-flow-name;
                                }
                        }
                        description
                            "Flow name in flow configuration list.";
                }

                leaf acl-table-name {
                    type string {
                                pattern '[a-zA-Z0-9]{1}([-a-zA-Z0-9_]{0,31})';
                                length 1..32;
                        }

                    description
                        "ACL table name used in IFA TailStamping flow configuration table.";
                }

                leaf acl-rule-name {
                    type string {
                                pattern '[a-zA-Z0-9]{1}([-a-zA-Z0-9_]{0,31})';
                                length 1..32;
                        }
                    description
                        "ACL rule name used in IFA TailStamping flow configuration table.";
                }

               container state {
                        sonic-ext:db-name "COUNTERS_DB"; 
                        sonic-ext:key-delim ":";    

                        config false;
                        description "State data for TAM INT IFA FS FLOW";

                        leaf MATCHED_PACKETS {
                                type yang:counter64;
                                default 0;
                                description
                                    "Number of packets matching IFA TailStamping flow.";
                        }

                        leaf MATCHED_OCTETS {
                                type yang:counter64;
                                default 0;
                                description
                                    "Number of octets matching IFA TailStamping flow.";
                        }
                }
            }
        }
    }
}
