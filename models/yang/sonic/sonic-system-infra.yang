module sonic-system-infra {
    namespace "http://github.com/Azure/sonic-system-infra";
    prefix sonic-sinfra;
    yang-version 1;


    organization
        "SONiC";

    contact
        "SONiC";

    description
        "System Infra rpc commands";

    revision 2020-05-27 {
        description
            "Initial revision.";
    }

    rpc config {
        description
            "Switch config operations:
                - reload: Clear current configuration and import a..."; 
        input {
            leaf param {
                type string {
                    pattern "reload";
                }
            }
        }
        output {
            leaf result {
                type string;
                description
                    "String showing the result of the last requested command (reload).";
            }
        }
    }

}
